OKBALFA-MIB DEFINITIONS ::= BEGIN

IMPORTS
        enterprises
                FROM RFC1155-SMI
        OBJECT-TYPE,INTEGER
                FROM RFC-1212
        DisplayString
                FROM RFC-1213
        mib-2
                FROM RFC-2578;
------------------------------------------------------------------
system 	OBJECT IDENTIFIER ::= {mib-2 1 }
---1.3.6.1.2.1.1
okbalfa OBJECT IDENTIFIER ::= {enterprises  57170}
---1.3.6.1.4.1.57170
okbalfa_V0 OBJECT IDENTIFIER ::= {enterprises 50001}
---1.3.6.1.4.1.50001
RTRS OBJECT IDENTIFIER ::= {enterprises 3}
_RTRS OBJECT IDENTIFIER ::= {RTRS 2}
RTRS-Param OBJECT IDENTIFIER ::= {_RTRS 1}
---1.3.6.1.4.1.3.2.1.0.0
RTRS-RDS-Param OBJECT IDENTIFIER ::= {_RTRS 3}
---1.3.6.1.4.1.3.2.3.0.0
------------------------------------------------------------------
RadioExciterV0        OBJECT IDENTIFIER ::= {okbalfa_V0 10}
------------------------------------------------------------------
----------------------V28-----------------------------------------
------------------------------------------------------------------
RadioExciter              OBJECT IDENTIFIER ::= {okbalfa 0}
RadioExciter-Info         OBJECT IDENTIFIER ::= {RadioExciter 1}
RadioExciter-Param        OBJECT IDENTIFIER ::= {RadioExciter 2}
RadioExciter-ParamMod     OBJECT IDENTIFIER ::= {RadioExciter 3}
RadioExciter-ParamStatus  OBJECT IDENTIFIER ::= {RadioExciter 4}
--RadioExciter-Trap       OBJECT IDENTIFIER ::= {RadioExciter 5}
RadioExciter-Setting      OBJECT IDENTIFIER ::= {RadioExciter 6}
------------------------------------------------------------------
Amplifier             OBJECT IDENTIFIER ::= {okbalfa 1}
Amplifier-Info        OBJECT IDENTIFIER ::= {Amplifier 1}
Amplifier-Param       OBJECT IDENTIFIER ::= {Amplifier 2}
Amplifier-Setting     OBJECT IDENTIFIER ::= {Amplifier 3}
Amplifier-Status      OBJECT IDENTIFIER ::= {Amplifier 4}
------------------------------------------------------------------
BlockControl          OBJECT IDENTIFIER ::= {okbalfa 2}
BlockControl-Info     OBJECT IDENTIFIER ::= {BlockControl 1}
BlockControl-Param    OBJECT IDENTIFIER ::= {BlockControl 2}
BlockControl-Setting  OBJECT IDENTIFIER ::= {BlockControl 3}
BlockControl-Status   OBJECT IDENTIFIER ::= {BlockControl 4}
------------------------------------------------------------------
------------------------------------------------------------------
------------------------------------------------------------------
DigitalExciter          OBJECT IDENTIFIER ::= {okbalfa 3}
DigitalExciter-Info     OBJECT IDENTIFIER ::= {DigitalExciter 1}
DigitalExciter-Param    OBJECT IDENTIFIER ::= {DigitalExciter 2}
DigitalExciter-Setting  OBJECT IDENTIFIER ::= {DigitalExciter 3}
DigitalExciter-Status   OBJECT IDENTIFIER ::= {DigitalExciter 4}
DigitalExciter-options  OBJECT IDENTIFIER ::= {DigitalExciter 5}
------------------------------------------------------------------
------------------------------------------------------------------
------------------------------------------------------------------
BlockControl_v2         OBJECT IDENTIFIER ::= {okbalfa 4}
------------------------------------------------------------------
BlockControl1            OBJECT IDENTIFIER ::={BlockControl_v2 1}
BlockControl1-Info      OBJECT IDENTIFIER ::= {BlockControl1 1}
BlockControl1-Param     OBJECT IDENTIFIER ::= {BlockControl1 2}
BlockControl1-Setting   OBJECT IDENTIFIER ::= {BlockControl1 3}
BlockControl1-Status    OBJECT IDENTIFIER ::= {BlockControl1 4}
------------------------------------------------------------------
Amplifier1           OBJECT IDENTIFIER ::= {BlockControl_v2 2}
Amplifier1-Info      OBJECT IDENTIFIER ::= {Amplifier1 1}
Amplifier1-Param     OBJECT IDENTIFIER ::= {Amplifier1 2}
Amplifier1-Setting   OBJECT IDENTIFIER ::= {Amplifier1 3}
Amplifier1-Status    OBJECT IDENTIFIER ::= {Amplifier1 4}
------------------------------------------------------------------
Amplifier2           OBJECT IDENTIFIER ::= {BlockControl_v2 3}
Amplifier2-Info      OBJECT IDENTIFIER ::= {Amplifier2 1}
Amplifier2-Param     OBJECT IDENTIFIER ::= {Amplifier2 2}
Amplifier2-Setting   OBJECT IDENTIFIER ::= {Amplifier2 3}
Amplifier2-Status    OBJECT IDENTIFIER ::= {Amplifier2 4}
------------------------------------------------------------------
Amplifier3           OBJECT IDENTIFIER ::= {BlockControl_v2 4}
Amplifier3-Info      OBJECT IDENTIFIER ::= {Amplifier3 1}
Amplifier3-Param     OBJECT IDENTIFIER ::= {Amplifier3 2}
Amplifier3-Setting   OBJECT IDENTIFIER ::= {Amplifier3 3}
Amplifier3-Status    OBJECT IDENTIFIER ::= {Amplifier3 4}
------------------------------------------------------------------
Amplifier4           OBJECT IDENTIFIER ::= {BlockControl_v2 5}
Amplifier4-Info      OBJECT IDENTIFIER ::= {Amplifier4 1}
Amplifier4-Param     OBJECT IDENTIFIER ::= {Amplifier4 2}
Amplifier4-Setting   OBJECT IDENTIFIER ::= {Amplifier4 3}
Amplifier4-Status    OBJECT IDENTIFIER ::= {Amplifier4 4}
------------------------------------------------------------------
RadioExciter1              OBJECT IDENTIFIER ::= {BlockControl_v2 6}
RadioExciter1-Info         OBJECT IDENTIFIER ::= {RadioExciter1 1}
RadioExciter1-Param        OBJECT IDENTIFIER ::= {RadioExciter1 2}
RadioExciter1-Status       OBJECT IDENTIFIER ::= {RadioExciter1 4}
------------------------------------------------------------------
RadioExciter2              OBJECT IDENTIFIER ::= {BlockControl_v2 7}
RadioExciter2-Info         OBJECT IDENTIFIER ::= {RadioExciter2 1}
RadioExciter2-Param        OBJECT IDENTIFIER ::= {RadioExciter2 2}
RadioExciter2-Status       OBJECT IDENTIFIER ::= {RadioExciter2 4}
------------------------------------------------------------------
DigitalExciter1          OBJECT IDENTIFIER ::= {BlockControl_v2 8}
DigitalExciter1-Info     OBJECT IDENTIFIER ::= {DigitalExciter1 1}
DigitalExciter1-Param    OBJECT IDENTIFIER ::= {DigitalExciter1 2}
DigitalExciter1-Status   OBJECT IDENTIFIER ::= {DigitalExciter1 4}
------------------------------------------------------------------
DigitalExciter2          OBJECT IDENTIFIER ::= {BlockControl_v2 9}
DigitalExciter2-Info     OBJECT IDENTIFIER ::= {DigitalExciter2 1}
DigitalExciter2-Param    OBJECT IDENTIFIER ::= {DigitalExciter2 2}
DigitalExciter2-Status   OBJECT IDENTIFIER ::= {DigitalExciter2 4}
------------------------------------------------------------------
AVR1_1          OBJECT IDENTIFIER ::= {BlockControl_v2 10}
AVR1_1-Info     OBJECT IDENTIFIER ::= {AVR1_1 1}
AVR1_1-Param    OBJECT IDENTIFIER ::= {AVR1_1 2}
AVR1_1-Status   OBJECT IDENTIFIER ::= {AVR1_1 4}
------------------------------------------------------------------
------------------------------------------------------------------
------------------------------------------------------------------
AVR                      OBJECT IDENTIFIER ::= {okbalfa 5}
AVR-Info                 OBJECT IDENTIFIER ::= {AVR 1}
AVR-Param                OBJECT IDENTIFIER ::= {AVR 2}
AVR-Setting              OBJECT IDENTIFIER ::= {AVR 3}
AVR-Main-Transmiter1     OBJECT IDENTIFIER ::= {AVR 10}
AVR-Main-Transmiter2     OBJECT IDENTIFIER ::= {AVR 11}
AVR-Main-Transmiter3     OBJECT IDENTIFIER ::= {AVR 12}
AVR-Reserv-Transmiter    OBJECT IDENTIFIER ::= {AVR 13}
--------------------------------------------------------------------
Transmiter1-Param     OBJECT IDENTIFIER ::= {AVR-Main-Transmiter1 2}
Transmiter1-Setting   OBJECT IDENTIFIER ::= {AVR-Main-Transmiter1 3}
Transmiter1-Status    OBJECT IDENTIFIER ::= {AVR-Main-Transmiter1 4}
--------------------------------------------------------------------
Transmiter2-Param     OBJECT IDENTIFIER ::= {AVR-Main-Transmiter2 2}
Transmiter2-Setting   OBJECT IDENTIFIER ::= {AVR-Main-Transmiter2 3}
Transmiter2-Status    OBJECT IDENTIFIER ::= {AVR-Main-Transmiter2 4}
--------------------------------------------------------------------
Transmiter3-Param     OBJECT IDENTIFIER ::= {AVR-Main-Transmiter3 2}
Transmiter3-Setting   OBJECT IDENTIFIER ::= {AVR-Main-Transmiter3 3}
Transmiter3-Status    OBJECT IDENTIFIER ::= {AVR-Main-Transmiter3 4}
--------------------------------------------------------------------
TransmiterReserv-Param     OBJECT IDENTIFIER ::= {AVR-Reserv-Transmiter 2}
TransmiterReserv-Setting   OBJECT IDENTIFIER ::= {AVR-Reserv-Transmiter 3}
TransmiterReserv-Status    OBJECT IDENTIFIER ::= {AVR-Reserv-Transmiter 4}
--------------------------------------------------------------------
--------------------------------------------------------------------
--------------------------------------------------------------------
Repeater                  OBJECT IDENTIFIER ::= {okbalfa 6}
Repeater-Info             OBJECT IDENTIFIER ::= {Repeater 1}
Repeater-Param            OBJECT IDENTIFIER ::= {Repeater 2}
Repeater-Setting          OBJECT IDENTIFIER ::= {Repeater 3}
Repeater-Status           OBJECT IDENTIFIER ::= {Repeater 4}
------------------------------------------------------------------
-----------------------RTRS---------------------------------------
------------------------------------------------------------------
RTRS-SerNumer OBJECT-TYPE
  SYNTAX  DisplayString
  ACCESS  read-only
  STATUS  mandatory
  DESCRIPTION
  ::= {RTRS-Param 0}
----------------------------------------------------------------------
RTRS-TypeDevice OBJECT-TYPE
  SYNTAX  DisplayString
  ACCESS  read-only
  STATUS  mandatory
  DESCRIPTION
  ::= {RTRS-Param 1}
----------------------------------------------------------------------
RTRS-StatusDevice OBJECT-TYPE
  SYNTAX  INTEGER {ON(1),OFF(0)}
  ACCESS  read-only
  STATUS  current
  DESCRIPTION
  ::= {RTRS-Param 2}
----------------------------------------------------------------------
RTRS-P-Out OBJECT-TYPE
  SYNTAX  INTEGER
  ACCESS  read-only
  STATUS  current
  DESCRIPTION
        "Output power(divider=10,W)"
  ::= {RTRS-Param 3}
----------------------------------------------------------------------
RTRS-P-ref OBJECT-TYPE
  SYNTAX  INTEGER
  ACCESS  read-only
  STATUS  current
  DESCRIPTION
        "Reflected power(divider=10,W)"
  ::= {RTRS-Param 4}
----------------------------------------------------------------------
RTRS-U1 OBJECT-TYPE
  SYNTAX  INTEGER
  ACCESS  read-only
  STATUS  current
  DESCRIPTION
          "Power Supply Voltage,V"
  ::= {RTRS-Param 5}
----------------------------------------------------------------------
RTRS-I1 OBJECT-TYPE
  SYNTAX  INTEGER
  ACCESS  read-only
  STATUS  current
  DESCRIPTION
          "end-stage current,A"
  ::= {RTRS-Param 6}
----------------------------------------------------------------------
RTRS-Frequency OBJECT-TYPE
  SYNTAX  INTEGER
  ACCESS  read-only
  STATUS  current
  DESCRIPTION
    "Value, KHz"
  ::= {RTRS-Param 8}
----------------------------------------------------------------------
RTRS-Level-Sound OBJECT-TYPE
  SYNTAX  INTEGER
  ACCESS  read-only
  STATUS  current
  DESCRIPTION
    "Left channel Value, dB"
  ::= {RTRS-Param 9}
----------------------------------------------------------------------
RTRS-T OBJECT-TYPE
  SYNTAX  INTEGER
  ACCESS  read-only
  STATUS  current
  DESCRIPTION
          "Value, Celsius degree"
  ::= {RTRS-Param 10}
----------------------------------------------------------------------
RTRS-RadioText OBJECT-TYPE
  SYNTAX  DisplayString
  ACCESS  read-write
  STATUS  mandatory
  DESCRIPTION
  ::= {RTRS-RDS-Param 0}
----------------------------------------------------------------------
------------------Системные ------------------------------------------
----------------------------------------------------------------------
sysUpTime OBJECT-TYPE
  SYNTAX  TimeTicks
  ACCESS  read-only
  STATUS  mandatory
  DESCRIPTION
          "The time (in hundredths of a second) since the network management portion of the system was last re-initialized."
  ::= {system 3}

sysName OBJECT-TYPE
    SYNTAX      DisplayString (SIZE (0..255))
    ACCESS  read-only
    STATUS  mandatory
    DESCRIPTION
            ""
    ::= { system 5 }
----------------------------------------------------------------------
-----------------RadioExciter-----------------------------------------
----------------------------------------------------------------------
RadioExciter-SerNumer OBJECT-TYPE
  SYNTAX  DisplayString
  ACCESS  read-only
  STATUS  mandatory
  DESCRIPTION
          "Serial number of the device"
  ::= {RadioExciter-Info 1}
----------------------------------------------------------------------
-----------------------Версия ПО -------------------------------------
----------------------------------------------------------------------
RadioExciter-Software OBJECT-TYPE
  SYNTAX  DisplayString
  ACCESS  read-only
  STATUS  mandatory
  DESCRIPTION
          "Software application"
  ::= {RadioExciter-Info 2}
----------------------------------------------------------------------
RadioExciter-Software-Boot OBJECT-TYPE
  SYNTAX  DisplayString
  ACCESS  read-only
  STATUS  mandatory
  DESCRIPTION
          "Software bootloader"
  ::= {RadioExciter-Info 3}
----------------------------------------------------------------------
RadioExciter-Software-board OBJECT-TYPE
  SYNTAX  DisplayString
  ACCESS  read-only
  STATUS  mandatory
  DESCRIPTION
          "PCB version"
  ::= {RadioExciter-Info 4}
----------------------------------------------------------------------
RadioExciter-Software-Audio OBJECT-TYPE
  SYNTAX  DisplayString
  ACCESS  read-only
  STATUS  mandatory
  DESCRIPTION
          "Software Audio MCU"
  ::= {RadioExciter-Info 5}

----------------------------------------------------------------------
--------------------------Power --------------------------------------
----------------------------------------------------------------------


RadioExciter-PowerOut OBJECT-TYPE
  SYNTAX  INTEGER
  ACCESS  read-only
  STATUS  current
  DESCRIPTION
          "Output power, W"
  ::= {RadioExciter-Param 1}
----------------------------------------------------------------------
RadioExciter-PowerRef OBJECT-TYPE
  SYNTAX  INTEGER
  ACCESS  read-only
  STATUS  current
  DESCRIPTION
          "PowerRef ,W"
  ::= {RadioExciter-Param 2}
----------------------------------------------------------------------
RadioExciter-SWR OBJECT-TYPE
  SYNTAX  INTEGER
  ACCESS  read-only
  STATUS  current
  DESCRIPTION
          "Value/100"
  ::= {RadioExciter-Param 3}
----------------------------------------------------------------------
RadioExciter-PowerBallast OBJECT-TYPE
  SYNTAX  INTEGER
  ACCESS  read-only
  STATUS  current
  DESCRIPTION
          "Ballast power, W"
  ::= {RadioExciter-Param 5}
----------------------------------------------------------------------
RadioExciter-I1 OBJECT-TYPE
  SYNTAX  INTEGER
  ACCESS  read-only
  STATUS  current
  DESCRIPTION
          "Value/10, A"
  ::= {RadioExciter-Param 20}
----------------------------------------------------------------------
RadioExciter-I2 OBJECT-TYPE
  SYNTAX  INTEGER
  ACCESS  read-only
  STATUS  current
  DESCRIPTION
          "Value/10, A"
  ::= {RadioExciter-Param 21}
----------------------------------------------------------------------
RadioExciter-I3 OBJECT-TYPE
  SYNTAX  INTEGER
  ACCESS  read-only
  STATUS  current
  DESCRIPTION
          "Value/10, A"
  ::= {RadioExciter-Param 22}
----------------------------------------------------------------------
RadioExciter-U1 OBJECT-TYPE
  SYNTAX  INTEGER
  ACCESS  read-only
  STATUS  current
  DESCRIPTION
          "Value/10, V"
  ::= {RadioExciter-Param 10}
----------------------------------------------------------------------
RadioExciter-U2 OBJECT-TYPE
  SYNTAX  INTEGER
  ACCESS  read-only
  STATUS  current
  DESCRIPTION
          "Value/10, V"
  ::= {RadioExciter-Param 11}
----------------------------------------------------------------------
RadioExciter-U3 OBJECT-TYPE
  SYNTAX  INTEGER
  ACCESS  read-only
  STATUS  current
  DESCRIPTION
          "Value/10, V"
  ::= {RadioExciter-Param 12}
----------------------------------------------------------------------
RadioExciter-PosU12 OBJECT-TYPE
  SYNTAX  INTEGER
  ACCESS  read-only
  STATUS  current
  DESCRIPTION
          "Value/10, V"
  ::= {RadioExciter-Param 13}
----------------------------------------------------------------------
RadioExciter-NegU12 OBJECT-TYPE
  SYNTAX  INTEGER
  ACCESS  read-only
  STATUS  current
  DESCRIPTION
          "Value/10, V"
  ::= {RadioExciter-Param 14}
----------------------------------------------------------------------
RadioExciter-Temperature OBJECT-TYPE
  SYNTAX  INTEGER
  ACCESS  read-only
  STATUS  current
  DESCRIPTION
          "Value/10, Celsius degree"
  ::= {RadioExciter-Param 30}
----------------------------------------------------------------------
----------------------------------------------------------------------
----------------------------------------------------------------------
RadioExciter-mod-Deviation OBJECT-TYPE
  SYNTAX  INTEGER
  ACCESS  read-only
  STATUS  current
  DESCRIPTION
          "Value/10, kHz"
  ::= {RadioExciter-ParamMod 1}
----------------------------------------------------------------------
RadioExciter-mod-Frequency OBJECT-TYPE
  SYNTAX  INTEGER
  ACCESS  read-only
  STATUS  current
  DESCRIPTION
		"Value/100, MHz"
  ::= {RadioExciter-ParamMod 2}
----------------------------------------------------------------------
RadioExciter-mod-Lvl-Left OBJECT-TYPE
  SYNTAX  INTEGER
  ACCESS  read-only
  STATUS  current
  DESCRIPTION
          "Value/10, dB"
  ::= {RadioExciter-ParamMod 3}
----------------------------------------------------------------------
RadioExciter-mod-Lvl-Right OBJECT-TYPE
  SYNTAX  INTEGER
  ACCESS  read-only
  STATUS  current
  DESCRIPTION
          "Value/10, dB"
  ::= {RadioExciter-ParamMod 4}
----------------------------------------------------------------------
-----------------------Статусы параметров-----------------------------
----------------------------------------------------------------------
RadioExciter-status-Pout OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 1}
----------------------------------------------------------------------
----------------------------------------------------------------------
RadioExciter-status-PowerRef OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 2}
----------------------------------------------------------------------
RadioExciter-status-SWR OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 3}
----------------------------------------------------------------------
RadioExciter-status-PowerBallast OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 5}
----------------------------------------------------------------------
RadioExciter-status-I1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 20}
----------------------------------------------------------------------
RadioExciter-status-I2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 21}
----------------------------------------------------------------------
RadioExciter-status-I3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 22}
----------------------------------------------------------------------
RadioExciter-status-U1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 10}
----------------------------------------------------------------------
RadioExciter-status-U2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 11}
----------------------------------------------------------------------
RadioExciter-status-U3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 12}
----------------------------------------------------------------------
RadioExciter-status-PosU12 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 13}
----------------------------------------------------------------------
RadioExciter-status-NegU12 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 14}
----------------------------------------------------------------------
RadioExciter-status-Temperature OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter-ParamStatus 30}
----------------------------------------------------------------------
----------------------------------------------------------------------
----------------------------------------------------------------------
RadioExciter-power-on-off OBJECT-TYPE
  SYNTAX  INTEGER{OFF(0),ON(1)}
  ACCESS  write-only
  STATUS  mandatory
  DESCRIPTION
          "OFF(0),ON(1)"
  ::= {RadioExciter-Setting 1}
----------------------------------------------------------------------
RadioExciter-status-power-on-off OBJECT-TYPE
  SYNTAX  INTEGER{OFF_USER(0),ON(1),OFF_WEB(2),OFF_RTC(3)}
  ACCESS  read-only
  STATUS  mandatory
  DESCRIPTION
          ""
  ::= {RadioExciter-Setting 2}
----------------------------------------------------------------------
RadioExciter-Set-Connect-BlockControl OBJECT-TYPE
  SYNTAX  INTEGER{OFF(0),ON(1)}
  ACCESS  write-only
  STATUS  mandatory
  DESCRIPTION
          "OFF(0),ON(1)"
  ::= {RadioExciter-Setting 3}  
----------------------------------------------------------------------
----------------------------------------------------------------------
RadioExciter-RadioText OBJECT-TYPE
  SYNTAX  DisplayString
  ACCESS  read-write
  STATUS  mandatory
  DESCRIPTION
  ::= {RadioExciter-Setting 4} 
----------------------------------------------------------------------
----------------------------------------------------------------------
RadioExciter-Bootloader OBJECT-TYPE
  SYNTAX  INTEGER{ACCESS_DENIED(0),ACCESS_ALLOWED(1)}
  ACCESS  read-write
  STATUS  mandatory
  DESCRIPTION
  ::= {RadioExciter-Setting 6}
----------------------------------------------------------------------
----------------------------------------------------------------------
----------------------------------------------------------------------
RadioExciter-Watchdog OBJECT-TYPE
  SYNTAX  INTEGER{ACCESS_DENIED(0),ACCESS_ALLOWED(1)}
  ACCESS  read-write
  STATUS  mandatory
  DESCRIPTION
  ::= {RadioExciter-Setting 7}  
----------------------------------------------------------------------
----------------------------------------------------------------------
RadioExciter-RetryTime  OBJECT-TYPE
  SYNTAX  INTEGER
  ACCESS  read-write
  STATUS  current
  DESCRIPTION
    "Retry Time TCP connection, ms"
  ::= {RadioExciter-Setting 10}  
----------------------------------------------------------------------
----------------------------------------------------------------------
RadioExciter-RetryCount  OBJECT-TYPE
  SYNTAX  INTEGER
  ACCESS  read-write
  STATUS  mandatory
  DESCRIPTION
    "Number of tcp reconnections"  
  ::= {RadioExciter-Setting 11}    
----------------------------------------------------------------------
----------------------------------------------------------------------
RadioExciter-KeepAlive   OBJECT-TYPE
  SYNTAX  INTEGER
  ACCESS  read-write
  STATUS  mandatory
  DESCRIPTION
    "KeepAlive, ms"  
  ::= {RadioExciter-Setting 12}      
----------------------------------------------------------------------
----------------------------------------------------------------------
RadioExciter-PeriodHttpRequest OBJECT-TYPE
  SYNTAX  INTEGER
  ACCESS  read-write
  STATUS  mandatory
  DESCRIPTION
    "Period, HTTP request, s"  
  ::= {RadioExciter-Setting 13}
----------------------------------------------------------------------
----------------------------------------------------------------------
RadioExciter-TypeHttpServer OBJECT-TYPE
  SYNTAX  INTEGER
  ACCESS  read-write
  STATUS  mandatory
  DESCRIPTION
    "2 is new HttpServer"
  ::= {RadioExciter-Setting 20}
----------------------------------------------------------------------
RadioExciter-Reboot-mcu OBJECT-TYPE
  SYNTAX  INTEGER
  ACCESS  read-write
  STATUS  mandatory
  DESCRIPTION
    "Reboot-mcu"
  ::= {RadioExciter-Setting 30}
----------------------------------------------------------------------
RadioExciter-Reboot-Ethernet OBJECT-TYPE
  SYNTAX  INTEGER
  ACCESS  read-write
  STATUS  mandatory
  DESCRIPTION
    "Reboot Ethernet"
  ::= {RadioExciter-Setting 31}
 

----------------------------------------------------------------------
RadioExciter-Date OBJECT-TYPE
  SYNTAX  DisplayString
  ACCESS  read-write
  STATUS  mandatory
  DESCRIPTION
      "get data in format YYYY-MM-DD HH:MM:SS Set data in format YYYY-MM-DDTHH:MM:SS"
  ::= {RadioExciter-Setting 40}

----------------------------------------------------------------------
  RadioExciter-AudioSwitchToMain OBJECT-TYPE
  SYNTAX  INTEGER
  ACCESS  write-only
  STATUS  mandatory
  DESCRIPTION
          "1 - switch to main channel"
  ::= {RadioExciter-Setting 50}
----------------------------------------------------------------------
  RadioExciter-AudioSwitchToBackup OBJECT-TYPE
  SYNTAX  INTEGER
  ACCESS  write-only
  STATUS  mandatory
  DESCRIPTION
          "1 - switch to backup channel"
  ::= {RadioExciter-Setting 51}

----------------------------------------------------------------------
-----------------Amplifier--------------------------------------------
----------------------------------------------------------------------

----------------------------------------------------------------------
-----------------Amplifier-Setting------------------------------------
----------------------------------------------------------------------

----------------------------------------------------------------------
Amplifier-Reset-web OBJECT-TYPE
  SYNTAX  INTEGER{reset(1)}
  ACCESS  write-only
  STATUS  mandatory
  DESCRIPTION
          "Reset http"
  ::= {Amplifier-Setting 1}
----------------------------------------------------------------------
-----------Включить/Выключить загрузчик-------------------------------
----------------------------------------------------------------------
Amplifier-Access-Boot OBJECT-TYPE
  SYNTAX  INTEGER{ACCESS_DENIED(0),ACCESS_ALLOWED(1)}
  ACCESS  write-only
  STATUS  mandatory
  DESCRIPTION
          "ACCESS_DENIED(0),ACCESS_ALLOWED(1))"
  ::= {Amplifier-Setting 2}
----------------------------------------------------------------------
Amplifier-Access-web-reset-1h OBJECT-TYPE
  SYNTAX  INTEGER{DISABLE(0),ENABLE(1)}
  ACCESS  write-only
  STATUS  mandatory
  DESCRIPTION
          "DISABLE(0),ENABLE(1))"
  ::= {Amplifier-Setting 3}
----------------------------------------------------------------------
-----------Состояние БП1 (вкл,выкл)-----------------------------------
----------------------------------------------------------------------
Status-PS1 OBJECT-TYPE
  SYNTAX  INTEGER{STATUS_OFF(0),STATUS_OK(1),STATUS_WEB_OFF(4),STATUS_BLOCK(5)}
  ACCESS  read-only
  STATUS  mandatory
  DESCRIPTION
          "Status of the device, power supply 1"
  ::= {Amplifier-Setting 10}
----------------------------------------------------------------------
-----------Состояние БП2 (вкл,выкл)---------------------------------
----------------------------------------------------------------------
Status-PS2 OBJECT-TYPE
  SYNTAX  INTEGER{STATUS_OFF(0),STATUS_OK(1),STATUS_WEB_OFF(4),STATUS_BLOCK(5)}
  ACCESS  read-only
  STATUS  mandatory
  DESCRIPTION
          "Status of the device, power supply 2"
  ::= {Amplifier-Setting 11}
----------------------------------------------------------------------
-----------Перезагрузка процессора -----------------------------------
----------------------------------------------------------------------
Amplifier-reboot-mcu OBJECT-TYPE
  SYNTAX  INTEGER{ON(1)}
  ACCESS  write
  STATUS  mandatory
  DESCRIPTION
          "Reboot Amplifier"
  ::= {Amplifier-Setting 12}
----------------------------------------------------------------------
----------------------------------------------------------------------
Amplifier-RetryTime  OBJECT-TYPE
  SYNTAX  INTEGER
  ACCESS  read-write
  STATUS  current
  DESCRIPTION
    "Retry Time TCP connection, ms"
  ::= {Amplifier-Setting 15}  
----------------------------------------------------------------------
----------------------------------------------------------------------
Amplifier-RetryCount  OBJECT-TYPE
  SYNTAX  INTEGER
  ACCESS  read-write
  STATUS  mandatory
  DESCRIPTION
    "Number of tcp reconnections"  
  ::= {Amplifier-Setting 16}    
----------------------------------------------------------------------
----------------------------------------------------------------------
Amplifier-KeepAlive   OBJECT-TYPE
  SYNTAX  INTEGER
  ACCESS  read-write
  STATUS  mandatory
  DESCRIPTION
    "KeepAlive, ms"  
  ::= {Amplifier-Setting 17}   

----------------------------------------------------------------------
-----------------------Версия ПО -------------------------------------
----------------------------------------------------------------------

----------------------------------------------------------------------
Amplifier-SerNumer OBJECT-TYPE
  SYNTAX  DisplayString
  ACCESS  read-only
  STATUS  mandatory
  DESCRIPTION
          "Serial number of the device"
  ::= {Amplifier-Info 1}
----------------------------------------------------------------------
Amplifier-Software OBJECT-TYPE
  SYNTAX  DisplayString
  ACCESS  read-only
  STATUS  mandatory
  DESCRIPTION
          "Software application"
  ::= {Amplifier-Info 2}
----------------------------------------------------------------------
Amplifier-Software-Boot OBJECT-TYPE
  SYNTAX  DisplayString
  ACCESS  read-only
  STATUS  mandatory
  DESCRIPTION
          "Software bootloader"
  ::= {Amplifier-Info 3}
----------------------------------------------------------------------
Amplifier-Software-board OBJECT-TYPE
  SYNTAX  DisplayString
  ACCESS  read-only
  STATUS  mandatory
  DESCRIPTION
          "PCB version"
  ::= {Amplifier-Info 4}
----------------------------------------------------------------------
-----------------------Param Amplifier--------------------------------
----------------------------------------------------------------------
Amplifier-PowerOut OBJECT-TYPE
  SYNTAX  INTEGER
  ACCESS  read-only
  STATUS  current
  DESCRIPTION
          "Output power, W"
  ::= {Amplifier-Param 1}
----------------------------------------------------------------------
Amplifier-PowerRef OBJECT-TYPE
  SYNTAX  INTEGER
  ACCESS  read-only
  STATUS  current
  DESCRIPTION
          "PowerRef ,W"
  ::= {Amplifier-Param 2}
----------------------------------------------------------------------
Amplifier-SWR OBJECT-TYPE
  SYNTAX  INTEGER
  ACCESS  read-only
  STATUS  current
  DESCRIPTION
          "Value/100"
  ::= {Amplifier-Param 3}
----------------------------------------------------------------------
Amplifier-Pin OBJECT-TYPE
  SYNTAX  INTEGER
  ACCESS  read-only
  STATUS  current
  DESCRIPTION
          "Value, W"
  ::= {Amplifier-Param 4}
----------------------------------------------------------------------
Amplifier-PowerBallast OBJECT-TYPE
  SYNTAX  INTEGER
  ACCESS  read-only
  STATUS  current
  DESCRIPTION
          "Ballast power, W"
  ::= {Amplifier-Param 5}
----------------------------------------------------------------------
Amplifier-U1 OBJECT-TYPE
  SYNTAX  INTEGER
  ACCESS  read-only
  STATUS  current
  DESCRIPTION
          "Value/10, V"
  ::= {Amplifier-Param 10}
----------------------------------------------------------------------
Amplifier-U2 OBJECT-TYPE
  SYNTAX  INTEGER
  ACCESS  read-only
  STATUS  current
  DESCRIPTION
          "Value/10, V"
  ::= {Amplifier-Param 11}
----------------------------------------------------------------------
Amplifier-U3 OBJECT-TYPE
  SYNTAX  INTEGER
  ACCESS  read-only
  STATUS  current
  DESCRIPTION
          "Value/10, V"
  ::= {Amplifier-Param 12}
----------------------------------------------------------------------
Amplifier-I1 OBJECT-TYPE
  SYNTAX  INTEGER
  ACCESS  read-only
  STATUS  current
  DESCRIPTION
          "Value/10, A"
  ::= {Amplifier-Param 20}
----------------------------------------------------------------------
Amplifier-I2 OBJECT-TYPE
  SYNTAX  INTEGER
  ACCESS  read-only
  STATUS  current
  DESCRIPTION
          "Value/10, A"
  ::= {Amplifier-Param 21}
  ----------------------------------------------------------------------
Amplifier-I3 OBJECT-TYPE
  SYNTAX  INTEGER
  ACCESS  read-only
  STATUS  current
  DESCRIPTION
          "Value/10, A"
  ::= {Amplifier-Param 22}
  ----------------------------------------------------------------------
Amplifier-I4 OBJECT-TYPE
  SYNTAX  INTEGER
  ACCESS  read-only
  STATUS  current
  DESCRIPTION
          "Value/10, A"
  ::= {Amplifier-Param 23}
----------------------------------------------------------------------
Amplifier-Temperature OBJECT-TYPE
  SYNTAX  INTEGER
  ACCESS  read-only
  STATUS  current
  DESCRIPTION
          "Celsius degree"
  ::= {Amplifier-Param 30}

----------------------------------------------------------------------
-----------------------status Amplifier--------------------------------
----------------------------------------------------------------------
Amplifier-status-PowerOut OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 1}
----------------------------------------------------------------------
Amplifier-status-PowerRef OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 2}
----------------------------------------------------------------------
Amplifier-status-SWR OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 3}  
----------------------------------------------------------------------
Amplifier-status-Pin OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 4}  
----------------------------------------------------------------------
Amplifier-status-PowerBallast OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 5}
----------------------------------------------------------------------
Amplifier-status-U1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 10}
----------------------------------------------------------------------
Amplifier-status-U2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 11}
----------------------------------------------------------------------
Amplifier-status-U3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 12}
----------------------------------------------------------------------
Amplifier-status-I1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 20}  
----------------------------------------------------------------------
Amplifier-status-I2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 21}
----------------------------------------------------------------------
Amplifier-status-I3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 22}
----------------------------------------------------------------------
Amplifier-status-I4 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier-Status 23}   
----------------------------------------------------------------------
Amplifier-status-T OBJECT-TYPE
  SYNTAX  INTEGER{TempIsNotExist(0),TempIsNorm(1),TempIsOverheat(3)}
  ACCESS  read-only
  STATUS  current
  DESCRIPTION
          ""
  ::= {Amplifier-Status 30}
----------------------------------------------------------------------
-----------------BlockControl-----------------------------------------
----------------------------------------------------------------------

----------------------------------------------------------------------
-----------------------BlockControl Setting---------------------------
----------------------------------------------------------------------



----------------------------------------------------------------------
BlockControl-Reset-web OBJECT-TYPE
  SYNTAX  INTEGER{reset(1)}
  ACCESS  write-only
  STATUS  mandatory
  DESCRIPTION
          "Reset http"
  ::= {BlockControl-Setting 1}
----------------------------------------------------------------------
BlockControl-Access-Boot OBJECT-TYPE
  SYNTAX  INTEGER{ACCESS_DENIED(0),ACCESS_ALLOWED(1)}
  ACCESS  write-only
  STATUS  mandatory
  DESCRIPTION
          "ACCESS_DENIED(0),ACCESS_ALLOWED(1))"
  ::= {BlockControl-Setting 2}
----------------------------------------------------------------------
BlockControl-Access-web-reset-1h OBJECT-TYPE
  SYNTAX  INTEGER{DISABLE(0),ENABLE(1)}
  ACCESS  write-only
  STATUS  mandatory
  DESCRIPTION
          "DISABLE(0),ENABLE(1))"
  ::= {BlockControl-Setting 3}
----------------------------------------------------------------------
BlockControl-Reboot OBJECT-TYPE
  SYNTAX  INTEGER{ENABLE(1)}
  ACCESS  write-only
  STATUS  mandatory
  DESCRIPTION
          "Block reboot"
  ::= {BlockControl-Setting 4}

----------------------------------------------------------------------
-----------------------Версия ПО BlockControl-------------------------
----------------------------------------------------------------------


BlockControl-SerNumer OBJECT-TYPE
  SYNTAX  DisplayString
  ACCESS  read-only
  STATUS  mandatory
  DESCRIPTION
          "Serial number of the device"
  ::= {BlockControl-Info 1}
----------------------------------------------------------------------
BlockControl-Software OBJECT-TYPE
  SYNTAX  DisplayString
  ACCESS  read-only
  STATUS  mandatory
  DESCRIPTION
          "Software application"
  ::= {BlockControl-Info 2}
----------------------------------------------------------------------
BlockControl-Software-Boot OBJECT-TYPE
  SYNTAX  DisplayString
  ACCESS  read-only
  STATUS  mandatory
  DESCRIPTION
          "Software bootloader"
  ::= {BlockControl-Info 3}
----------------------------------------------------------------------
BlockControl-Software-board OBJECT-TYPE
  SYNTAX  DisplayString
  ACCESS  read-only
  STATUS  mandatory
  DESCRIPTION
          "PCB version"
  ::= {BlockControl-Info 4}


----------------------------------------------------------------------
-----------------------Param-BlockControl-----------------------------
----------------------------------------------------------------------


BlockControl-PowerOut OBJECT-TYPE
  SYNTAX  INTEGER
  ACCESS  read-only
  STATUS  current
  DESCRIPTION
          "Output power, W"
  ::= {BlockControl-Param 1}
----------------------------------------------------------------------
BlockControl-PowerRef OBJECT-TYPE
  SYNTAX  INTEGER
  ACCESS  read-only
  STATUS  current
  DESCRIPTION
          "Output power, W"
  ::= {BlockControl-Param 2}
----------------------------------------------------------------------
BlockControl-PowerSWR OBJECT-TYPE
  SYNTAX  INTEGER
  ACCESS  read-only
  STATUS  current
  DESCRIPTION
          "Value/100"
  ::= {BlockControl-Param 3}
----------------------------------------------------------------------
BlockControl-PowerBallast1 OBJECT-TYPE
  SYNTAX  INTEGER
  ACCESS  read-only
  STATUS  current
  DESCRIPTION
          "Ballast power, W"
  ::= {BlockControl-Param 5}
----------------------------------------------------------------------
BlockControl-PowerBallast2 OBJECT-TYPE
  SYNTAX  INTEGER
  ACCESS  read-only
  STATUS  current
  DESCRIPTION
          "Ballast power, W"
  ::= {BlockControl-Param 6}
----------------------------------------------------------------------
BlockControl-PowerBallast3 OBJECT-TYPE
  SYNTAX  INTEGER
  ACCESS  read-only
  STATUS  current
  DESCRIPTION
          "Ballast power, W"
  ::= {BlockControl-Param 7}
----------------------------------------------------------------------
BlockControl-Temperature OBJECT-TYPE
  SYNTAX  INTEGER
  ACCESS  read-only
  STATUS  current
  DESCRIPTION
          "Celsius degree"
  ::= {BlockControl-Param 30}
----------------------------------------------------------------------
----------------------------------------------------------------------
----------------------------------------------------------------------
----------------------------------------------------------------------
BlockControl-Status-PowerOut OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl-Status 1} 
----------------------------------------------------------------------
BlockControl-Status-PowerRef OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl-Status 2}
----------------------------------------------------------------------
BlockControl-Status-PowerSWR OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl-Status 3}
----------------------------------------------------------------------
BlockControl-Status-PowerBallast1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl-Status 5}
----------------------------------------------------------------------
BlockControl-Status-PowerBallast2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl-Status 6}
----------------------------------------------------------------------
BlockControl-Status-PowerBallast3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl-Status 7}
----------------------------------------------------------------------
BlockControl-Status-Temperature OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl-Status 30}
----------------------------------------------------------------------
-----------------------RadioExciterV0---------------------------------
----------------------------------------------------------------------
Voltage OBJECT-TYPE
  SYNTAX INTEGER
  ACCESS read-only
  STATUS current
  DESCRIPTION
    "Voltage in volts"
  ::= {RadioExciterV0 161}
----------------------------------------------------------------------
I OBJECT-TYPE
  SYNTAX INTEGER
  ACCESS read-only
  STATUS current
  DESCRIPTION
    ""
  ::= {RadioExciterV0 165}
----------------------------------------------------------------------
Temperature OBJECT-TYPE
  SYNTAX INTEGER
  ACCESS read-only
  STATUS current
  DESCRIPTION
      "Temperature in Celsius"
  ::= {RadioExciterV0 169}
----------------------------------------------------------------------
Output-Power OBJECT-TYPE
  SYNTAX INTEGER
  ACCESS read-only
  STATUS current
  DESCRIPTION
      "Output power in watts*10"
  ::= {RadioExciterV0 172}
----------------------------------------------------------------------
Reflected-Power OBJECT-TYPE
  SYNTAX INTEGER
  ACCESS read-only
  STATUS current
  DESCRIPTION
      "Reflected power in watts*10"
  ::= {RadioExciterV0 173}
----------------------------------------------------------------------
Sound-Level OBJECT-TYPE
  SYNTAX INTEGER {-12dB(0),-11dB(1),-10dB(2),-9dB(3),-8dB(4),-7dB(5),-6dB(6),-5dB(7),-4dB(8),-3dB(9),-2dB(10),-1dB(11),0dB(12),1dB(13),2dB(14),3dB(15)}
  ACCESS read-only
  STATUS current
  DESCRIPTION
        "Range is -12dB(0) - 3dB(15)"
  ::= {RadioExciterV0 181}
----------------------------------------------------------------------
Output-Power-Restriction OBJECT-TYPE
    SYNTAX INTEGER {ON(1), OFF(0)}
    ACCESS read-only
    STATUS current
    DESCRIPTION
    ::= {RadioExciterV0 184}
----------------------------------------------------------------------
Mode OBJECT-TYPE
  SYNTAX INTEGER {MONO(1), STEREO(0)}
  ACCESS read-only
  STATUS current
  DESCRIPTION
  ::= {RadioExciterV0 185}
----------------------------------------------------------------------
Carrier-Frequency OBJECT-TYPE
  SYNTAX INTEGER
  ACCESS read-only
  STATUS current
  DESCRIPTION
    "Frequency in kHz"
  ::= {RadioExciterV0 186}
----------------------------------------------------------------------
Exciter-Power-supply OBJECT-TYPE
  SYNTAX INTEGER {ON(1), OFF(0)}
  ACCESS write
  STATUS current
  DESCRIPTION
  ::= {RadioExciterV0 180}
----------------------------------------------------------------------
Ethernet-Power-Control OBJECT-TYPE
  SYNTAX INTEGER {ON(1), OFF(1)}
  ACCESS write
  STATUS current
  DESCRIPTION
    "Output power in watts*10"
  ::= {RadioExciterV0 187}
----------------------------------------------------------------------
Serial-Number OBJECT-TYPE
  SYNTAX INTEGER
  ACCESS read-only
  STATUS current
  DESCRIPTION
  ::= {RadioExciterV0 300}
----------------------------------------------------------------------
Version-Software OBJECT-TYPE
  SYNTAX INTEGER
  ACCESS read-only
  STATUS current
  DESCRIPTION
  ::= {RadioExciterV0 301}
----------------------------------------------------------------------
Version-Bootloader OBJECT-TYPE
  SYNTAX INTEGER
  ACCESS read-only
  STATUS current
  DESCRIPTION
    "Bootloader version - 1 byte. Senior tetrad - number of version, junior tetrad - numberof subversion"
  ::= {RadioExciterV0 302}
----------------------------------------------------------------------
Connection-Status OBJECT-TYPE
  SYNTAX INTEGER {ENABLED(1), DISABLED(0)}
  ACCESS read-only
  STATUS current
  DESCRIPTION
  ::= {RadioExciterV0 310}
----------------------------------------------------------------------
----------------------------------------------------------------------

----------------------------------------------------------------------
---------------------Версия ПО DigitalExciter-------------------------
----------------------------------------------------------------------
DigitalExciter-SerNumer OBJECT-TYPE
  SYNTAX  DisplayString
  ACCESS  read-only
  STATUS  mandatory
  DESCRIPTION
          "Serial number of the device"
  ::= {DigitalExciter-Info 1}
----------------------------------------------------------------------
DigitalExciter-Software OBJECT-TYPE
  SYNTAX  DisplayString
  ACCESS  read-only
  STATUS  mandatory
  DESCRIPTION
          "Software application"
  ::= {DigitalExciter-Info 2}
----------------------------------------------------------------------
DigitalExciter-Software-Boot OBJECT-TYPE
  SYNTAX  DisplayString
  ACCESS  read-only
  STATUS  mandatory
  DESCRIPTION
          "Software bootloader"
  ::= {DigitalExciter-Info 3}
----------------------------------------------------------------------
DigitalExciter-Software-board OBJECT-TYPE
  SYNTAX  DisplayString
  ACCESS  read-only
  STATUS  mandatory
  DESCRIPTION
          "PCB version"
  ::= {DigitalExciter-Info 4}
----------------------------------------------------------------------
----------------------------------------------------------------------
----------------------------------------------------------------------
DigitalExciter-PowerOut OBJECT-TYPE
  SYNTAX  INTEGER
  ACCESS  read-only
  STATUS  current
  DESCRIPTION
          "Output power, W"
  ::= {DigitalExciter-Param 1}
----------------------------------------------------------------------
DigitalExciter-PowerRef OBJECT-TYPE
  SYNTAX  INTEGER
  ACCESS  read-only
  STATUS  current
  DESCRIPTION
          "PowerRef ,W"
  ::= {DigitalExciter-Param 2}
----------------------------------------------------------------------
DigitalExciter-SWR OBJECT-TYPE
  SYNTAX  INTEGER
  ACCESS  read-only
  STATUS  current
  DESCRIPTION
          "Value/100"
  ::= {DigitalExciter-Param 3}
----------------------------------------------------------------------
DigitalExciter-Pin OBJECT-TYPE
  SYNTAX  INTEGER
  ACCESS  read-only
  STATUS  current
  DESCRIPTION
          "Value, µW"
  ::= {DigitalExciter-Param 4}
----------------------------------------------------------------------
DigitalExciter-PowerBallast OBJECT-TYPE
  SYNTAX  INTEGER
  ACCESS  read-only
  STATUS  current
  DESCRIPTION
          "Ballast power, W"
  ::= {DigitalExciter-Param 5}
----------------------------------------------------------------------
DigitalExciter-U1 OBJECT-TYPE
  SYNTAX  INTEGER
  ACCESS  read-only
  STATUS  current
  DESCRIPTION
          "Value/10, V"
  ::= {DigitalExciter-Param 10}
----------------------------------------------------------------------
DigitalExciter-U2 OBJECT-TYPE
  SYNTAX  INTEGER
  ACCESS  read-only
  STATUS  current
  DESCRIPTION
          "Value/10, V"
  ::= {DigitalExciter-Param 11}
----------------------------------------------------------------------
DigitalExciter-I1 OBJECT-TYPE
  SYNTAX  INTEGER
  ACCESS  read-only
  STATUS  current
  DESCRIPTION
          "Value/10, A"
  ::= {DigitalExciter-Param 20}
  ----------------------------------------------------------------------
DigitalExciter-I2 OBJECT-TYPE
  SYNTAX  INTEGER
  ACCESS  read-only
  STATUS  current
  DESCRIPTION
          "Value/10, A"
  ::= {DigitalExciter-Param 21}
  ----------------------------------------------------------------------
DigitalExciter-I3 OBJECT-TYPE
  SYNTAX  INTEGER
  ACCESS  read-only
  STATUS  current
  DESCRIPTION
          "Value/10, A"
  ::= {DigitalExciter-Param 22}  
  ----------------------------------------------------------------------
DigitalExciter-I4 OBJECT-TYPE
  SYNTAX  INTEGER
  ACCESS  read-only
  STATUS  current
  DESCRIPTION
          "Value/10, A"
  ::= {DigitalExciter-Param 23}    
----------------------------------------------------------------------
DigitalExciter-Temperature OBJECT-TYPE
  SYNTAX  INTEGER
  ACCESS  read-only
  STATUS  current
  DESCRIPTION
          "Value/10, Celsius degree"
  ::= {DigitalExciter-Param 30}
----------------------------------------------------------------------
--------------------------STATUS--------------------------------------
----------------------------------------------------------------------
DigitalExciter-status-PowerOut OBJECT-TYPE
  SYNTAX  INTEGER{STATUS_LOW_FAIL(3),STATUS_OK(1),STATUS_ALARM(2),STATUS_FAIL(3),NOT_USED(255)}
  ACCESS  read-only
  STATUS  current
  DESCRIPTION
          "Output power, W"
  ::= {DigitalExciter-Status 1}
----------------------------------------------------------------------
DigitalExciter-status-PowerRef OBJECT-TYPE
  SYNTAX  INTEGER{STATUS_LOW_FAIL(3),STATUS_OK(1),STATUS_ALARM(2),STATUS_FAIL(3),NOT_USED(255)}
  ACCESS  read-only
  STATUS  current
  DESCRIPTION
          "PowerRef ,W"
  ::= {DigitalExciter-Status 2}
----------------------------------------------------------------------
DigitalExciter-status-SWR OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/100"
  ::= {DigitalExciter-Status 3}
----------------------------------------------------------------------
DigitalExciter-status-Pin OBJECT-TYPE
  SYNTAX  INTEGER{STATUS_LOW_FAIL(3),STATUS_OK(1),STATUS_ALARM(2),STATUS_FAIL(3),NOT_USED(255)}
  ACCESS  read-only
  STATUS  current
  DESCRIPTION
          "Value, µW"
  ::= {DigitalExciter-Status 4}
----------------------------------------------------------------------
DigitalExciter-status-PowerBallast OBJECT-TYPE
  SYNTAX  INTEGER{STATUS_LOW_FAIL(3),STATUS_OK(1),STATUS_ALARM(2),STATUS_FAIL(3),NOT_USED(255)}
  ACCESS  read-only
  STATUS  current
  DESCRIPTION
          "Ballast power, W"
  ::= {DigitalExciter-Status 5}
----------------------------------------------------------------------
DigitalExciter-status-U1 OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/10, V"
  ::= {DigitalExciter-Status 10}
----------------------------------------------------------------------
DigitalExciter-status-U2 OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/10, V"
  ::= {DigitalExciter-Status 11}
----------------------------------------------------------------------
DigitalExciter-status-I1 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter-Status 20}
  ----------------------------------------------------------------------
DigitalExciter-status-I2 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter-Status 21}
  ----------------------------------------------------------------------
DigitalExciter-status-I3 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter-Status 22}  
  ----------------------------------------------------------------------
DigitalExciter-status-I4 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter-Status 23}  
----------------------------------------------------------------------
DigitalExciter-status-Temperature OBJECT-TYPE
  SYNTAX  INTEGER{STATUS_LOW_FAIL(3),STATUS_OK(1),STATUS_ALARM(2),STATUS_FAIL(3),NOT_USED(255)}
  ACCESS  read-only
  STATUS  current
  DESCRIPTION
          "Celsius degree"
  ::= {DigitalExciter-Status 30}  
----------------------------------------------------------------------
----------------------------------------------------------------------
----------------------------------------------------------------------
DigitalExciter-power-on-off OBJECT-TYPE
  SYNTAX  INTEGER{OFF(4),ON(1)}
  ACCESS  read-write
  STATUS  mandatory
  DESCRIPTION
          ""
  ::= {DigitalExciter-Setting 1}
----------------------------------------------------------------------
DigitalExciter-reboot OBJECT-TYPE
  SYNTAX  INTEGER{ON(1)}
  ACCESS  write
  STATUS  mandatory
  DESCRIPTION
          "Reboot device"
  ::= {DigitalExciter-Setting 2}
----------------------------------------------------------------------
----------------------------------------------------------------------
----------------------------------------------------------------------

----------------------------------------------------------------------
----------------------------------------------------------------------
----------------------------------------------------------------------
----------------------------------------------------------------------
DigitalExciter-options-Access-Boot OBJECT-TYPE
  SYNTAX  INTEGER{ON(0),OFF(1)}
  ACCESS  read-write
  STATUS  mandatory
  DESCRIPTION
          "Bootloader on/off"
  ::= {DigitalExciter-options 1}
----------------------------------------------------------------------
DigitalExciter-options-Web-Reset OBJECT-TYPE
  SYNTAX  INTEGER{ON(1)}
  ACCESS  write-only
  STATUS  mandatory
  DESCRIPTION
          "Web reset"
  ::= {DigitalExciter-options 2}
----------------------------------------------------------------------
DigitalExciter-options-web-reset-1h OBJECT-TYPE
  SYNTAX  INTEGER{OFF(0),ON(1)}
  ACCESS  read-write
  STATUS  mandatory
  DESCRIPTION
          "Restart web every hour"
  ::= {DigitalExciter-options 3}

----------------------------------------------------------------------
----------------------------------------------------------------------
----------------------------------------------------------------------
----------------------------------------------------------------------  



----------------------------------------------------------------------
-----------------------Версия ПО BlockControl-------------------------
----------------------------------------------------------------------

----------------------------------------------------------------------
----------------------------------------------------------------------
-----------------------Версия ПО--------------------------------------
----------------------------------------------------------------------
----------------------------------------------------------------------
BlockControl1-SerNumer OBJECT-TYPE
  SYNTAX  DisplayString
  ACCESS  read-only
  STATUS  mandatory
  DESCRIPTION
          "Serial number of the device"
  ::= {BlockControl1-Info 1}
----------------------------------------------------------------------
BlockControl1-Software OBJECT-TYPE
  SYNTAX  DisplayString
  ACCESS  read-only
  STATUS  mandatory
  DESCRIPTION
          "Software application"
  ::= {BlockControl1-Info 2}
----------------------------------------------------------------------
BlockControl1-Software-Boot OBJECT-TYPE
  SYNTAX  DisplayString
  ACCESS  read-only
  STATUS  mandatory
  DESCRIPTION
          "Software bootloader"
  ::= {BlockControl1-Info 3}
----------------------------------------------------------------------
BlockControl1-Software-board OBJECT-TYPE
  SYNTAX  DisplayString
  ACCESS  read-only
  STATUS  mandatory
  DESCRIPTION
          "PCB version"
  ::= {BlockControl1-Info 4}
  ----------------------------------------------------------------------
BlockControl1-Software-board-rev OBJECT-TYPE
  SYNTAX  DisplayString
  ACCESS  read-only
  STATUS  mandatory
  DESCRIPTION
          "PCB revision"
  ::= {BlockControl1-Info 5}


----------------------------------------------------------------------
BlockControl1-Model OBJECT-TYPE
  SYNTAX  INTEGER{radio(0),digital(1)}
  ACCESS  read-only
  STATUS  mandatory
  DESCRIPTION
          "Model exciter radio or digital"
  ::= {BlockControl1-Info 5}
----------------------------------------------------------------------
BlockControl1-Number-of-exciter OBJECT-TYPE
  SYNTAX  DisplayString
  ACCESS  read-only
  STATUS  mandatory
  DESCRIPTION
          ""
  ::= {BlockControl1-Info 6}
----------------------------------------------------------------------
BlockControl1-Number-of-amplifier OBJECT-TYPE
  SYNTAX  DisplayString
  ACCESS  read-only
  STATUS  mandatory
  DESCRIPTION
          ""
  ::= {BlockControl1-Info 7}

----------------------------------------------------------------------
-----------------------Param-BlockControl-----------------------------
----------------------------------------------------------------------


BlockControl1-PowerOut OBJECT-TYPE
  SYNTAX  INTEGER
  ACCESS  read-only
  STATUS  current
  DESCRIPTION
          "Output power, W"
  ::= {BlockControl1-Param 1}
----------------------------------------------------------------------
BlockControl1-PowerRef OBJECT-TYPE
  SYNTAX  INTEGER
  ACCESS  read-only
  STATUS  current
  DESCRIPTION
          "Output power, W"
  ::= {BlockControl1-Param 2}
----------------------------------------------------------------------
BlockControl1-PowerSWR OBJECT-TYPE
  SYNTAX  INTEGER
  ACCESS  read-only
  STATUS  current
  DESCRIPTION
          "Value/100"
  ::= {BlockControl1-Param 3}
----------------------------------------------------------------------
BlockControl1-PowerBallast1 OBJECT-TYPE
  SYNTAX  INTEGER
  ACCESS  read-only
  STATUS  current
  DESCRIPTION
          "Ballast power, W"
  ::= {BlockControl1-Param 4}
----------------------------------------------------------------------
BlockControl1-PowerBallast2 OBJECT-TYPE
  SYNTAX  INTEGER
  ACCESS  read-only
  STATUS  current
  DESCRIPTION
          "Ballast power, W"
  ::= {BlockControl1-Param 5}
----------------------------------------------------------------------
BlockControl1-PowerBallast3 OBJECT-TYPE
  SYNTAX  INTEGER
  ACCESS  read-only
  STATUS  current
  DESCRIPTION
          "Ballast power, W"
  ::= {BlockControl1-Param 6}
----------------------------------------------------------------------
BlockControl1-Temperature OBJECT-TYPE
  SYNTAX  INTEGER
  ACCESS  read-only
  STATUS  current
  DESCRIPTION
          "Celsius degree"
  ::= {BlockControl1-Param 7}
----------------------------------------------------------------------
----------------------------------------------------------------------
----------------------------------------------------------------------
BlockControl1-Access-Boot OBJECT-TYPE
  SYNTAX  INTEGER{ACCESS_DENIED(0),ACCESS_ALLOWED(1)}
  ACCESS  read-write
  STATUS  mandatory
  DESCRIPTION
          "ACCESS_DENIED(0),ACCESS_ALLOWED(1))"
  ::= {BlockControl1-Setting 1}
----------------------------------------------------------------------
----------- Перезагрузка BlockControl --------------------------------
----------------------------------------------------------------------
BlockControl1-reboot OBJECT-TYPE
  SYNTAX  INTEGER{Reboot(1)}
  ACCESS  write-only
  STATUS  mandatory
  DESCRIPTION
          "Reboot BlockControl1"
  ::= {BlockControl1-Setting 2}
----------------------------------------------------------------------
----------------------------------------------------------------------
----------------------------------------------------------------------
----------------------------------------------------------------------
BlockControl1-Status-PowerOut OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl1-Status 1} 
----------------------------------------------------------------------
BlockControl1-Status-PowerRef OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl1-Status 2}
----------------------------------------------------------------------
BlockControl1-Status-PowerSWR OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl1-Status 3}
----------------------------------------------------------------------
BlockControl1-Status-PowerBallast1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl1-Status 4}
----------------------------------------------------------------------
BlockControl1-Status-PowerBallast2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl1-Status 5}
----------------------------------------------------------------------
BlockControl1-Status-PowerBallast3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl1-Status 6}
----------------------------------------------------------------------
BlockControl1-Status-Temperature OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {BlockControl1-Status 7}

----------------------------------------------------------------------
-----------------------Версия ПО усилитель в БУ-----------------------
----------------------------------------------------------------------

----------------------------------------------------------------------
Amplifier1-SerNumer OBJECT-TYPE
  SYNTAX  DisplayString
  ACCESS  read-only
  STATUS  mandatory
  DESCRIPTION
          "Serial number of the device"
  ::= {Amplifier1-Info 1}
----------------------------------------------------------------------
Amplifier1-Software OBJECT-TYPE
  SYNTAX  DisplayString
  ACCESS  read-only
  STATUS  mandatory
  DESCRIPTION
          "Software application"
  ::= {Amplifier1-Info 2}
----------------------------------------------------------------------
Amplifier1-Software-Boot OBJECT-TYPE
  SYNTAX  DisplayString
  ACCESS  read-only
  STATUS  mandatory
  DESCRIPTION
          "Software bootloader"
  ::= {Amplifier1-Info 3}
----------------------------------------------------------------------
Amplifier1-Software-board OBJECT-TYPE
  SYNTAX  DisplayString
  ACCESS  read-only
  STATUS  mandatory
  DESCRIPTION
          "PCB version"
  ::= {Amplifier1-Info 4}
----------------------------------------------------------------------
----------------------------------------------------------------------
-----------------------Param Amplifier--------------------------------
----------------------------------------------------------------------
Amplifier1-PowerOut OBJECT-TYPE
  SYNTAX  INTEGER
  ACCESS  read-only
  STATUS  current
  DESCRIPTION
          "Output power, W"
  ::= {Amplifier1-Param 1}
----------------------------------------------------------------------
Amplifier1-PowerRef OBJECT-TYPE
  SYNTAX  INTEGER
  ACCESS  read-only
  STATUS  current
  DESCRIPTION
          "PowerRef ,W"
  ::= {Amplifier1-Param 2}
----------------------------------------------------------------------
Amplifier1-SWR OBJECT-TYPE
  SYNTAX  INTEGER
  ACCESS  read-only
  STATUS  current
  DESCRIPTION
          "Value/100"
  ::= {Amplifier1-Param 3}
----------------------------------------------------------------------
Amplifier1-Pin OBJECT-TYPE
  SYNTAX  INTEGER
  ACCESS  read-only
  STATUS  current
  DESCRIPTION
          "Value, W"
  ::= {Amplifier1-Param 4}
----------------------------------------------------------------------
Amplifier1-PowerBallast OBJECT-TYPE
  SYNTAX  INTEGER
  ACCESS  read-only
  STATUS  current
  DESCRIPTION
          "Ballast power, W"
  ::= {Amplifier1-Param 5}
----------------------------------------------------------------------
Amplifier1-U1 OBJECT-TYPE
  SYNTAX  INTEGER
  ACCESS  read-only
  STATUS  current
  DESCRIPTION
          "Value/10, V"
  ::= {Amplifier1-Param 10}
----------------------------------------------------------------------
Amplifier1-U2 OBJECT-TYPE
  SYNTAX  INTEGER
  ACCESS  read-only
  STATUS  current
  DESCRIPTION
          "Value/10, V"
  ::= {Amplifier1-Param 11}
----------------------------------------------------------------------
Amplifier1-U3 OBJECT-TYPE
  SYNTAX  INTEGER
  ACCESS  read-only
  STATUS  current
  DESCRIPTION
          "Value/10, V"
  ::= {Amplifier1-Param 12}
----------------------------------------------------------------------
Amplifier1-I1 OBJECT-TYPE
  SYNTAX  INTEGER
  ACCESS  read-only
  STATUS  current
  DESCRIPTION
          "Value/10, A"
  ::= {Amplifier1-Param 20}
----------------------------------------------------------------------
Amplifier1-I2 OBJECT-TYPE
  SYNTAX  INTEGER
  ACCESS  read-only
  STATUS  current
  DESCRIPTION
          "Value/10, A"
  ::= {Amplifier1-Param 21}
  ----------------------------------------------------------------------
Amplifier1-I3 OBJECT-TYPE
  SYNTAX  INTEGER
  ACCESS  read-only
  STATUS  current
  DESCRIPTION
          "Value/10, A"
  ::= {Amplifier1-Param 22}
  ----------------------------------------------------------------------
Amplifier1-I4 OBJECT-TYPE
  SYNTAX  INTEGER
  ACCESS  read-only
  STATUS  current
  DESCRIPTION
          "Value/10, A"
  ::= {Amplifier1-Param 23}
----------------------------------------------------------------------
Amplifier1-Temperature OBJECT-TYPE
  SYNTAX  INTEGER
  ACCESS  read-only
  STATUS  current
  DESCRIPTION
          "Value/10, Celsius degree"
  ::= {Amplifier1-Param 30}

----------------------------------------------------------------------
-----------------------status Amplifier--------------------------------
----------------------------------------------------------------------
Amplifier1-status-PowerOut OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 1}
----------------------------------------------------------------------
Amplifier1-status-PowerRef OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 2}
----------------------------------------------------------------------
Amplifier1-status-SWR OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 3}  
----------------------------------------------------------------------
Amplifier1-status-Pin OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 4}  
----------------------------------------------------------------------
Amplifier1-status-PowerBallast OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 5}
----------------------------------------------------------------------
Amplifier1-status-U1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 10}
----------------------------------------------------------------------
Amplifier1-status-U2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 11}
----------------------------------------------------------------------
Amplifier1-status-U3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 12}
----------------------------------------------------------------------
Amplifier1-status-I1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 20}  
----------------------------------------------------------------------
Amplifier1-status-I2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 21}
----------------------------------------------------------------------
Amplifier1-status-I3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 22}
----------------------------------------------------------------------
Amplifier1-status-I4 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier1-Status 23}   
----------------------------------------------------------------------
Amplifier1-status-T OBJECT-TYPE
  SYNTAX  INTEGER{TempIsNotExist(0),TempIsNorm(1),TempIsOverheat(3)}
  ACCESS  read-only
  STATUS  current
  DESCRIPTION
          ""
  ::= {Amplifier1-Status 30}

----------------------------------------------------------------------
----------------------------------------------------------------------
------------------Блок управление Усилитель 2-------------------------
----------------------------------------------------------------------
----------------------------------------------------------------------

----------------------------------------------------------------------
-----------------------Версия ПО -------------------------------------
----------------------------------------------------------------------

----------------------------------------------------------------------
Amplifier2-SerNumer OBJECT-TYPE
  SYNTAX  DisplayString
  ACCESS  read-only
  STATUS  mandatory
  DESCRIPTION
          "Serial number of the device"
  ::= {Amplifier2-Info 1}
----------------------------------------------------------------------
Amplifier2-Software OBJECT-TYPE
  SYNTAX  DisplayString
  ACCESS  read-only
  STATUS  mandatory
  DESCRIPTION
          "Software application"
  ::= {Amplifier2-Info 2}
----------------------------------------------------------------------
Amplifier2-Software-Boot OBJECT-TYPE
  SYNTAX  DisplayString
  ACCESS  read-only
  STATUS  mandatory
  DESCRIPTION
          "Software bootloader"
  ::= {Amplifier2-Info 3}
----------------------------------------------------------------------
Amplifier2-Software-board OBJECT-TYPE
  SYNTAX  DisplayString
  ACCESS  read-only
  STATUS  mandatory
  DESCRIPTION
          "PCB version"
  ::= {Amplifier2-Info 4}
----------------------------------------------------------------------
----------------------------------------------------------------------
-----------------------Param Amplifier--------------------------------
----------------------------------------------------------------------
Amplifier2-PowerOut OBJECT-TYPE
  SYNTAX  INTEGER
  ACCESS  read-only
  STATUS  current
  DESCRIPTION
          "Output power, W"
  ::= {Amplifier2-Param 1}
----------------------------------------------------------------------
Amplifier2-PowerRef OBJECT-TYPE
  SYNTAX  INTEGER
  ACCESS  read-only
  STATUS  current
  DESCRIPTION
          "PowerRef ,W"
  ::= {Amplifier2-Param 2}
----------------------------------------------------------------------
Amplifier2-SWR OBJECT-TYPE
  SYNTAX  INTEGER
  ACCESS  read-only
  STATUS  current
  DESCRIPTION
          "Value/100"
  ::= {Amplifier2-Param 3}
----------------------------------------------------------------------
Amplifier2-Pin OBJECT-TYPE
  SYNTAX  INTEGER
  ACCESS  read-only
  STATUS  current
  DESCRIPTION
          "Value, W"
  ::= {Amplifier2-Param 4}
----------------------------------------------------------------------
Amplifier2-PowerBallast OBJECT-TYPE
  SYNTAX  INTEGER
  ACCESS  read-only
  STATUS  current
  DESCRIPTION
          "Ballast power, W"
  ::= {Amplifier2-Param 5}
----------------------------------------------------------------------
Amplifier2-U1 OBJECT-TYPE
  SYNTAX  INTEGER
  ACCESS  read-only
  STATUS  current
  DESCRIPTION
          "Value/10, V"
  ::= {Amplifier2-Param 10}
----------------------------------------------------------------------
Amplifier2-U2 OBJECT-TYPE
  SYNTAX  INTEGER
  ACCESS  read-only
  STATUS  current
  DESCRIPTION
          "Value/10, V"
  ::= {Amplifier2-Param 11}
----------------------------------------------------------------------
Amplifier2-U3 OBJECT-TYPE
  SYNTAX  INTEGER
  ACCESS  read-only
  STATUS  current
  DESCRIPTION
          "Value/10, V"
  ::= {Amplifier2-Param 12}
----------------------------------------------------------------------
Amplifier2-I1 OBJECT-TYPE
  SYNTAX  INTEGER
  ACCESS  read-only
  STATUS  current
  DESCRIPTION
          "Value/10, A"
  ::= {Amplifier2-Param 20}
----------------------------------------------------------------------
Amplifier2-I2 OBJECT-TYPE
  SYNTAX  INTEGER
  ACCESS  read-only
  STATUS  current
  DESCRIPTION
          "Value/10, A"
  ::= {Amplifier2-Param 21}
  ----------------------------------------------------------------------
Amplifier2-I3 OBJECT-TYPE
  SYNTAX  INTEGER
  ACCESS  read-only
  STATUS  current
  DESCRIPTION
          "Value/10, A"
  ::= {Amplifier2-Param 22}
  ----------------------------------------------------------------------
Amplifier2-I4 OBJECT-TYPE
  SYNTAX  INTEGER
  ACCESS  read-only
  STATUS  current
  DESCRIPTION
          "Value/10, A"
  ::= {Amplifier2-Param 23}
----------------------------------------------------------------------
Amplifier2-Temperature OBJECT-TYPE
  SYNTAX  INTEGER
  ACCESS  read-only
  STATUS  current
  DESCRIPTION
          "Value/10,Celsius degree"
  ::= {Amplifier2-Param 30}

----------------------------------------------------------------------
-----------------------status Amplifier--------------------------------
----------------------------------------------------------------------
Amplifier2-status-PowerOut OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 1}
----------------------------------------------------------------------
Amplifier2-status-PowerRef OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 2}
----------------------------------------------------------------------
Amplifier2-status-SWR OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 3}  
----------------------------------------------------------------------
Amplifier2-status-Pin OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 4}  
----------------------------------------------------------------------
Amplifier2-status-PowerBallast OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 5}
----------------------------------------------------------------------
Amplifier2-status-U1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 10}
----------------------------------------------------------------------
Amplifier2-status-U2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 11}
----------------------------------------------------------------------
Amplifier2-status-U3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 12}
----------------------------------------------------------------------
Amplifier2-status-I1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 20}  
----------------------------------------------------------------------
Amplifier2-status-I2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 21}
----------------------------------------------------------------------
Amplifier2-status-I3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 22}
----------------------------------------------------------------------
Amplifier2-status-I4 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier2-Status 23}   
----------------------------------------------------------------------
Amplifier2-status-T OBJECT-TYPE
  SYNTAX  INTEGER{TempIsNotExist(0),TempIsNorm(1),TempIsOverheat(3)}
  ACCESS  read-only
  STATUS  current
  DESCRIPTION
          ""
  ::= {Amplifier2-Status 30}


----------------------------------------------------------------------
----------------------------------------------------------------------
------------------Блок управление Усилитель 3-------------------------
----------------------------------------------------------------------
----------------------------------------------------------------------

----------------------------------------------------------------------
-----------------------Версия ПО -------------------------------------
----------------------------------------------------------------------

----------------------------------------------------------------------
Amplifier3-SerNumer OBJECT-TYPE
  SYNTAX  DisplayString
  ACCESS  read-only
  STATUS  mandatory
  DESCRIPTION
          "Serial number of the device"
  ::= {Amplifier3-Info 1}
----------------------------------------------------------------------
Amplifier3-Software OBJECT-TYPE
  SYNTAX  DisplayString
  ACCESS  read-only
  STATUS  mandatory
  DESCRIPTION
          "Software application"
  ::= {Amplifier3-Info 2}
----------------------------------------------------------------------
Amplifier3-Software-Boot OBJECT-TYPE
  SYNTAX  DisplayString
  ACCESS  read-only
  STATUS  mandatory
  DESCRIPTION
          "Software bootloader"
  ::= {Amplifier3-Info 3}
----------------------------------------------------------------------
Amplifier3-Software-board OBJECT-TYPE
  SYNTAX  DisplayString
  ACCESS  read-only
  STATUS  mandatory
  DESCRIPTION
          "PCB version"
  ::= {Amplifier3-Info 4}
----------------------------------------------------------------------
----------------------------------------------------------------------
-----------------------Param Amplifier--------------------------------
----------------------------------------------------------------------
Amplifier3-PowerOut OBJECT-TYPE
  SYNTAX  INTEGER
  ACCESS  read-only
  STATUS  current
  DESCRIPTION
          "Output power, W"
  ::= {Amplifier3-Param 1}
----------------------------------------------------------------------
Amplifier3-PowerRef OBJECT-TYPE
  SYNTAX  INTEGER
  ACCESS  read-only
  STATUS  current
  DESCRIPTION
          "PowerRef ,W"
  ::= {Amplifier3-Param 2}
----------------------------------------------------------------------
Amplifier3-SWR OBJECT-TYPE
  SYNTAX  INTEGER
  ACCESS  read-only
  STATUS  current
  DESCRIPTION
          "Value/100"
  ::= {Amplifier3-Param 3}
----------------------------------------------------------------------
Amplifier3-Pin OBJECT-TYPE
  SYNTAX  INTEGER
  ACCESS  read-only
  STATUS  current
  DESCRIPTION
          "Value, W"
  ::= {Amplifier3-Param 4}
----------------------------------------------------------------------
Amplifier3-PowerBallast OBJECT-TYPE
  SYNTAX  INTEGER
  ACCESS  read-only
  STATUS  current
  DESCRIPTION
          "Ballast power, W"
  ::= {Amplifier3-Param 5}
----------------------------------------------------------------------
Amplifier3-U1 OBJECT-TYPE
  SYNTAX  INTEGER
  ACCESS  read-only
  STATUS  current
  DESCRIPTION
          "Value/10, V"
  ::= {Amplifier3-Param 10}
----------------------------------------------------------------------
Amplifier3-U2 OBJECT-TYPE
  SYNTAX  INTEGER
  ACCESS  read-only
  STATUS  current
  DESCRIPTION
          "Value/10, V"
  ::= {Amplifier3-Param 11}
----------------------------------------------------------------------
Amplifier3-U3 OBJECT-TYPE
  SYNTAX  INTEGER
  ACCESS  read-only
  STATUS  current
  DESCRIPTION
          "Value/10, V"
  ::= {Amplifier3-Param 12}
----------------------------------------------------------------------
Amplifier3-I1 OBJECT-TYPE
  SYNTAX  INTEGER
  ACCESS  read-only
  STATUS  current
  DESCRIPTION
          "Value/10, A"
  ::= {Amplifier3-Param 20}
----------------------------------------------------------------------
Amplifier3-I2 OBJECT-TYPE
  SYNTAX  INTEGER
  ACCESS  read-only
  STATUS  current
  DESCRIPTION
          "Value/10, A"
  ::= {Amplifier3-Param 21}
  ----------------------------------------------------------------------
Amplifier3-I3 OBJECT-TYPE
  SYNTAX  INTEGER
  ACCESS  read-only
  STATUS  current
  DESCRIPTION
          "Value/10, A"
  ::= {Amplifier3-Param 22}
  ----------------------------------------------------------------------
Amplifier3-I4 OBJECT-TYPE
  SYNTAX  INTEGER
  ACCESS  read-only
  STATUS  current
  DESCRIPTION
          "Value/10, A"
  ::= {Amplifier3-Param 23}
----------------------------------------------------------------------
Amplifier3-Temperature OBJECT-TYPE
  SYNTAX  INTEGER
  ACCESS  read-only
  STATUS  current
  DESCRIPTION
          "Value/10,Celsius degree"
  ::= {Amplifier3-Param 30}

----------------------------------------------------------------------
-----------------------status Amplifier--------------------------------
----------------------------------------------------------------------
Amplifier3-status-PowerOut OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 1}
----------------------------------------------------------------------
Amplifier3-status-PowerRef OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 2}
----------------------------------------------------------------------
Amplifier3-status-SWR OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 3}  
----------------------------------------------------------------------
Amplifier3-status-Pin OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 4}  
----------------------------------------------------------------------
Amplifier3-status-PowerBallast OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 5}
----------------------------------------------------------------------
Amplifier3-status-U1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 10}
----------------------------------------------------------------------
Amplifier3-status-U2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 11}
----------------------------------------------------------------------
Amplifier3-status-U3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 12}
----------------------------------------------------------------------
Amplifier3-status-I1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 20}  
----------------------------------------------------------------------
Amplifier3-status-I2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 21}
----------------------------------------------------------------------
Amplifier3-status-I3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 22}
----------------------------------------------------------------------
Amplifier3-status-I4 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier3-Status 23}   
----------------------------------------------------------------------
Amplifier3-status-T OBJECT-TYPE
  SYNTAX  INTEGER{TempIsNotExist(0),TempIsNorm(1),TempIsOverheat(3)}
  ACCESS  read-only
  STATUS  current
  DESCRIPTION
          ""
  ::= {Amplifier3-Status 30}


----------------------------------------------------------------------
----------------------------------------------------------------------
------------------Блок управление Усилитель 4-------------------------
----------------------------------------------------------------------
----------------------------------------------------------------------

----------------------------------------------------------------------
-----------------------Версия ПО -------------------------------------
----------------------------------------------------------------------

----------------------------------------------------------------------
Amplifier4-SerNumer OBJECT-TYPE
  SYNTAX  DisplayString
  ACCESS  read-only
  STATUS  mandatory
  DESCRIPTION
          "Serial number of the device"
  ::= {Amplifier4-Info 1}
----------------------------------------------------------------------
Amplifier4-Software OBJECT-TYPE
  SYNTAX  DisplayString
  ACCESS  read-only
  STATUS  mandatory
  DESCRIPTION
          "Software application"
  ::= {Amplifier4-Info 2}
----------------------------------------------------------------------
Amplifier4-Software-Boot OBJECT-TYPE
  SYNTAX  DisplayString
  ACCESS  read-only
  STATUS  mandatory
  DESCRIPTION
          "Software bootloader"
  ::= {Amplifier4-Info 3}
----------------------------------------------------------------------
Amplifier4-Software-board OBJECT-TYPE
  SYNTAX  DisplayString
  ACCESS  read-only
  STATUS  mandatory
  DESCRIPTION
          "PCB version"
  ::= {Amplifier4-Info 4}
----------------------------------------------------------------------
----------------------------------------------------------------------
-----------------------Param Amplifier--------------------------------
----------------------------------------------------------------------
Amplifier4-PowerOut OBJECT-TYPE
  SYNTAX  INTEGER
  ACCESS  read-only
  STATUS  current
  DESCRIPTION
          "Output power, W"
  ::= {Amplifier4-Param 1}
----------------------------------------------------------------------
Amplifier4-PowerRef OBJECT-TYPE
  SYNTAX  INTEGER
  ACCESS  read-only
  STATUS  current
  DESCRIPTION
          "PowerRef ,W"
  ::= {Amplifier4-Param 2}
----------------------------------------------------------------------
Amplifier4-SWR OBJECT-TYPE
  SYNTAX  INTEGER
  ACCESS  read-only
  STATUS  current
  DESCRIPTION
          "Value/100"
  ::= {Amplifier4-Param 3}
----------------------------------------------------------------------
Amplifier4-Pin OBJECT-TYPE
  SYNTAX  INTEGER
  ACCESS  read-only
  STATUS  current
  DESCRIPTION
          "Value, W"
  ::= {Amplifier4-Param 4}
----------------------------------------------------------------------
Amplifier4-PowerBallast OBJECT-TYPE
  SYNTAX  INTEGER
  ACCESS  read-only
  STATUS  current
  DESCRIPTION
          "Ballast power, W"
  ::= {Amplifier4-Param 5}
----------------------------------------------------------------------
Amplifier4-U1 OBJECT-TYPE
  SYNTAX  INTEGER
  ACCESS  read-only
  STATUS  current
  DESCRIPTION
          "Value/10, V"
  ::= {Amplifier4-Param 10}
----------------------------------------------------------------------
Amplifier4-U2 OBJECT-TYPE
  SYNTAX  INTEGER
  ACCESS  read-only
  STATUS  current
  DESCRIPTION
          "Value/10, V"
  ::= {Amplifier4-Param 11}
----------------------------------------------------------------------
Amplifier4-U3 OBJECT-TYPE
  SYNTAX  INTEGER
  ACCESS  read-only
  STATUS  current
  DESCRIPTION
          "Value/10, V"
  ::= {Amplifier4-Param 12}
----------------------------------------------------------------------
Amplifier4-I1 OBJECT-TYPE
  SYNTAX  INTEGER
  ACCESS  read-only
  STATUS  current
  DESCRIPTION
          "Value/10, A"
  ::= {Amplifier4-Param 20}
----------------------------------------------------------------------
Amplifier4-I2 OBJECT-TYPE
  SYNTAX  INTEGER
  ACCESS  read-only
  STATUS  current
  DESCRIPTION
          "Value/10, A"
  ::= {Amplifier4-Param 21}
  ----------------------------------------------------------------------
Amplifier4-I3 OBJECT-TYPE
  SYNTAX  INTEGER
  ACCESS  read-only
  STATUS  current
  DESCRIPTION
          "Value/10, A"
  ::= {Amplifier4-Param 22}
  ----------------------------------------------------------------------
Amplifier4-I4 OBJECT-TYPE
  SYNTAX  INTEGER
  ACCESS  read-only
  STATUS  current
  DESCRIPTION
          "Value/10, A"
  ::= {Amplifier4-Param 23}
----------------------------------------------------------------------
Amplifier4-Temperature OBJECT-TYPE
  SYNTAX  INTEGER
  ACCESS  read-only
  STATUS  current
  DESCRIPTION
          "Value/10,Celsius degree"
  ::= {Amplifier4-Param 30}

----------------------------------------------------------------------
-----------------------status Amplifier--------------------------------
----------------------------------------------------------------------
Amplifier4-status-PowerOut OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 1}
----------------------------------------------------------------------
Amplifier4-status-PowerRef OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 2}
----------------------------------------------------------------------
Amplifier4-status-SWR OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 3}  
----------------------------------------------------------------------
Amplifier4-status-Pin OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 4}  
----------------------------------------------------------------------
Amplifier4-status-PowerBallast OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 5}
----------------------------------------------------------------------
Amplifier4-status-U1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 10}
----------------------------------------------------------------------
Amplifier4-status-U2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 11}
----------------------------------------------------------------------
Amplifier4-status-U3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 12}
----------------------------------------------------------------------
Amplifier4-status-I1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 20}  
----------------------------------------------------------------------
Amplifier4-status-I2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 21}
----------------------------------------------------------------------
Amplifier4-status-I3 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 22}
----------------------------------------------------------------------
Amplifier4-status-I4 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Amplifier4-Status 23}   
----------------------------------------------------------------------
Amplifier4-status-T OBJECT-TYPE
  SYNTAX  INTEGER{TempIsNotExist(0),TempIsNorm(1),TempIsOverheat(3)}
  ACCESS  read-only
  STATUS  current
  DESCRIPTION
          ""
  ::= {Amplifier4-Status 30}


----------------------------------------------------------------------
----------------------------------------------------------------------
----------------------------------------------------------------------
-----------------Блок управление услитель РЦ первый-------------------
----------------------------------------------------------------------
----------------------------------------------------------------------
----------------------------------------------------------------------

----------------------------------------------------------------------
-----------------RadioExciter1-----------------------------------------
----------------------------------------------------------------------
RadioExciter1-SerNumer OBJECT-TYPE
  SYNTAX  DisplayString
  ACCESS  read-only
  STATUS  mandatory
  DESCRIPTION
          "Serial number of the device"
  ::= {RadioExciter1-Info 1}
----------------------------------------------------------------------
-----------------------Версия ПО -------------------------------------
----------------------------------------------------------------------
RadioExciter1-Software OBJECT-TYPE
  SYNTAX  DisplayString
  ACCESS  read-only
  STATUS  mandatory
  DESCRIPTION
          "Software application"
  ::= {RadioExciter1-Info 2}
----------------------------------------------------------------------
RadioExciter1-Software-Boot OBJECT-TYPE
  SYNTAX  DisplayString
  ACCESS  read-only
  STATUS  mandatory
  DESCRIPTION
          "Software bootloader"
  ::= {RadioExciter1-Info 3}
----------------------------------------------------------------------
RadioExciter1-Software-board OBJECT-TYPE
  SYNTAX  DisplayString
  ACCESS  read-only
  STATUS  mandatory
  DESCRIPTION
          "PCB version"
  ::= {RadioExciter1-Info 4}
----------------------------------------------------------------------
RadioExciter1-Software-Audio OBJECT-TYPE
  SYNTAX  DisplayString
  ACCESS  read-only
  STATUS  mandatory
  DESCRIPTION
          "Software Audio MCU"
  ::= {RadioExciter1-Info 5}

----------------------------------------------------------------------
--------------------------Power --------------------------------------
----------------------------------------------------------------------


RadioExciter1-PowerOut OBJECT-TYPE
  SYNTAX  INTEGER
  ACCESS  read-only
  STATUS  current
  DESCRIPTION
          "Output power, W"
  ::= {RadioExciter1-Param 1}
----------------------------------------------------------------------
RadioExciter1-PowerRef OBJECT-TYPE
  SYNTAX  INTEGER
  ACCESS  read-only
  STATUS  current
  DESCRIPTION
          "PowerRef ,W"
  ::= {RadioExciter1-Param 2}
----------------------------------------------------------------------
RadioExciter1-SWR OBJECT-TYPE
  SYNTAX  INTEGER
  ACCESS  read-only
  STATUS  current
  DESCRIPTION
          "Value/100"
  ::= {RadioExciter1-Param 3}
----------------------------------------------------------------------
RadioExciter1-PowerBallast OBJECT-TYPE
  SYNTAX  INTEGER
  ACCESS  read-only
  STATUS  current
  DESCRIPTION
          "Ballast power, W"
  ::= {RadioExciter1-Param 5}
----------------------------------------------------------------------
RadioExciter1-I1 OBJECT-TYPE
  SYNTAX  INTEGER
  ACCESS  read-only
  STATUS  current
  DESCRIPTION
          "Value/10, A"
  ::= {RadioExciter1-Param 20}
----------------------------------------------------------------------
RadioExciter1-I2 OBJECT-TYPE
  SYNTAX  INTEGER
  ACCESS  read-only
  STATUS  current
  DESCRIPTION
          "Value/10, A"
  ::= {RadioExciter1-Param 21}
----------------------------------------------------------------------
RadioExciter1-I3 OBJECT-TYPE
  SYNTAX  INTEGER
  ACCESS  read-only
  STATUS  current
  DESCRIPTION
          "Value/10, A"
  ::= {RadioExciter1-Param 22}
----------------------------------------------------------------------
RadioExciter1-U1 OBJECT-TYPE
  SYNTAX  INTEGER
  ACCESS  read-only
  STATUS  current
  DESCRIPTION
          "Value/10, V"
  ::= {RadioExciter1-Param 10}
----------------------------------------------------------------------
RadioExciter1-U2 OBJECT-TYPE
  SYNTAX  INTEGER
  ACCESS  read-only
  STATUS  current
  DESCRIPTION
          "Value/10, V"
  ::= {RadioExciter1-Param 11}
----------------------------------------------------------------------
RadioExciter1-U3 OBJECT-TYPE
  SYNTAX  INTEGER
  ACCESS  read-only
  STATUS  current
  DESCRIPTION
          "Value/10, V"
  ::= {RadioExciter1-Param 12}
----------------------------------------------------------------------
RadioExciter1-PosU12 OBJECT-TYPE
  SYNTAX  INTEGER
  ACCESS  read-only
  STATUS  current
  DESCRIPTION
          "Value/10, V"
  ::= {RadioExciter1-Param 13}
----------------------------------------------------------------------
RadioExciter1-NegU12 OBJECT-TYPE
  SYNTAX  INTEGER
  ACCESS  read-only
  STATUS  current
  DESCRIPTION
          "Value/10, V"
  ::= {RadioExciter1-Param 14}
----------------------------------------------------------------------
RadioExciter1-Temperature OBJECT-TYPE
  SYNTAX  INTEGER
  ACCESS  read-only
  STATUS  current
  DESCRIPTION
          "Value/10,Celsius degree"
  ::= {RadioExciter1-Param 30}

----------------------------------------------------------------------
-----------------------Статусы параметров-----------------------------
----------------------------------------------------------------------
RadioExciter1-status-Pout OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 1}
----------------------------------------------------------------------
----------------------------------------------------------------------
RadioExciter1-status-PowerRef OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 2}
----------------------------------------------------------------------
RadioExciter1-status-SWR OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 3}
----------------------------------------------------------------------
RadioExciter1-status-PowerBallast OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 5}
----------------------------------------------------------------------
RadioExciter1-status-I1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 20}
----------------------------------------------------------------------
RadioExciter1-status-I2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 21}
----------------------------------------------------------------------
RadioExciter1-status-I3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 22}
----------------------------------------------------------------------
RadioExciter1-status-U1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 10}
----------------------------------------------------------------------
RadioExciter1-status-U2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 11}
----------------------------------------------------------------------
RadioExciter1-status-U3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 12}
----------------------------------------------------------------------
RadioExciter1-status-PosU12 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 13}
----------------------------------------------------------------------
RadioExciter1-status-NegU12 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 14}
----------------------------------------------------------------------
RadioExciter1-status-Temperature OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter1-Status 30}


----------------------------------------------------------------------
----------------------------------------------------------------------
----------------------------------------------------------------------
-----------------Блок управление услитель РЦ второй-------------------
----------------------------------------------------------------------
----------------------------------------------------------------------
----------------------------------------------------------------------

----------------------------------------------------------------------
-----------------RadioExciter2-----------------------------------------
----------------------------------------------------------------------
RadioExciter2-SerNumer OBJECT-TYPE
  SYNTAX  DisplayString
  ACCESS  read-only
  STATUS  mandatory
  DESCRIPTION
          "Serial number of the device"
  ::= {RadioExciter2-Info 1}
----------------------------------------------------------------------
-----------------------Версия ПО -------------------------------------
----------------------------------------------------------------------
RadioExciter2-Software OBJECT-TYPE
  SYNTAX  DisplayString
  ACCESS  read-only
  STATUS  mandatory
  DESCRIPTION
          "Software application"
  ::= {RadioExciter2-Info 2}
----------------------------------------------------------------------
RadioExciter2-Software-Boot OBJECT-TYPE
  SYNTAX  DisplayString
  ACCESS  read-only
  STATUS  mandatory
  DESCRIPTION
          "Software bootloader"
  ::= {RadioExciter2-Info 3}
----------------------------------------------------------------------
RadioExciter2-Software-board OBJECT-TYPE
  SYNTAX  DisplayString
  ACCESS  read-only
  STATUS  mandatory
  DESCRIPTION
          "PCB version"
  ::= {RadioExciter2-Info 4}
----------------------------------------------------------------------
RadioExciter2-Software-Audio OBJECT-TYPE
  SYNTAX  DisplayString
  ACCESS  read-only
  STATUS  mandatory
  DESCRIPTION
          "Software Audio MCU"
  ::= {RadioExciter2-Info 5}

----------------------------------------------------------------------
--------------------------Power --------------------------------------
----------------------------------------------------------------------


RadioExciter2-PowerOut OBJECT-TYPE
  SYNTAX  INTEGER
  ACCESS  read-only
  STATUS  current
  DESCRIPTION
          "Output power, W"
  ::= {RadioExciter2-Param 1}
----------------------------------------------------------------------
RadioExciter2-PowerRef OBJECT-TYPE
  SYNTAX  INTEGER
  ACCESS  read-only
  STATUS  current
  DESCRIPTION
          "PowerRef ,W"
  ::= {RadioExciter2-Param 2}
----------------------------------------------------------------------
RadioExciter2-SWR OBJECT-TYPE
  SYNTAX  INTEGER
  ACCESS  read-only
  STATUS  current
  DESCRIPTION
          "Value/100"
  ::= {RadioExciter2-Param 3}
----------------------------------------------------------------------
RadioExciter2-PowerBallast OBJECT-TYPE
  SYNTAX  INTEGER
  ACCESS  read-only
  STATUS  current
  DESCRIPTION
          "Ballast power, W"
  ::= {RadioExciter2-Param 5}
----------------------------------------------------------------------
RadioExciter2-I1 OBJECT-TYPE
  SYNTAX  INTEGER
  ACCESS  read-only
  STATUS  current
  DESCRIPTION
          "Value/10, A"
  ::= {RadioExciter2-Param 20}
----------------------------------------------------------------------
RadioExciter2-I2 OBJECT-TYPE
  SYNTAX  INTEGER
  ACCESS  read-only
  STATUS  current
  DESCRIPTION
          "Value/10, A"
  ::= {RadioExciter2-Param 21}
----------------------------------------------------------------------
RadioExciter2-I3 OBJECT-TYPE
  SYNTAX  INTEGER
  ACCESS  read-only
  STATUS  current
  DESCRIPTION
          "Value/10, A"
  ::= {RadioExciter2-Param 22}
----------------------------------------------------------------------
RadioExciter2-U1 OBJECT-TYPE
  SYNTAX  INTEGER
  ACCESS  read-only
  STATUS  current
  DESCRIPTION
          "Value/10, V"
  ::= {RadioExciter2-Param 10}
----------------------------------------------------------------------
RadioExciter2-U2 OBJECT-TYPE
  SYNTAX  INTEGER
  ACCESS  read-only
  STATUS  current
  DESCRIPTION
          "Value/10, V"
  ::= {RadioExciter2-Param 11}
----------------------------------------------------------------------
RadioExciter2-U3 OBJECT-TYPE
  SYNTAX  INTEGER
  ACCESS  read-only
  STATUS  current
  DESCRIPTION
          "Value/10, V"
  ::= {RadioExciter2-Param 12}
----------------------------------------------------------------------
RadioExciter2-PosU12 OBJECT-TYPE
  SYNTAX  INTEGER
  ACCESS  read-only
  STATUS  current
  DESCRIPTION
          "Value/10, V"
  ::= {RadioExciter2-Param 13}
----------------------------------------------------------------------
RadioExciter2-NegU12 OBJECT-TYPE
  SYNTAX  INTEGER
  ACCESS  read-only
  STATUS  current
  DESCRIPTION
          "Value/10, V"
  ::= {RadioExciter2-Param 14}
----------------------------------------------------------------------
RadioExciter2-Temperature OBJECT-TYPE
  SYNTAX  INTEGER
  ACCESS  read-only
  STATUS  current
  DESCRIPTION
          "Value/10, Celsius degree"
  ::= {RadioExciter2-Param 30}

----------------------------------------------------------------------
-----------------------Статусы параметров-----------------------------
----------------------------------------------------------------------
RadioExciter2-status-Pout OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 1}
----------------------------------------------------------------------
----------------------------------------------------------------------
RadioExciter2-status-PowerRef OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 2}
----------------------------------------------------------------------
RadioExciter2-status-SWR OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 3}
----------------------------------------------------------------------
RadioExciter2-status-PowerBallast OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 5}
----------------------------------------------------------------------
RadioExciter2-status-I1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 20}
----------------------------------------------------------------------
RadioExciter2-status-I2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 21}
----------------------------------------------------------------------
RadioExciter2-status-I3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 22}
----------------------------------------------------------------------
RadioExciter2-status-U1 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 10}
----------------------------------------------------------------------
RadioExciter2-status-U2 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 11}
----------------------------------------------------------------------
RadioExciter2-status-U3 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 12}
----------------------------------------------------------------------
RadioExciter2-status-PosU12 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 13}
----------------------------------------------------------------------
RadioExciter2-status-NegU12 OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 14}
----------------------------------------------------------------------
RadioExciter2-status-Temperature OBJECT-TYPE
  SYNTAX  INTEGER{STATUS_LOW_FAIL(3),STATUS_OK(1),STATUS_ALARM(2),STATUS_FAIL(3),NOT_USED(255)}  
  ACCESS  read-only
  STATUS  current
  DESCRIPTION
          ""
  ::= {RadioExciter2-Status 30}

----------------------------------------------------------------------
----------------------------------------------------------------------
---------------------Блок управлеие модель СТ первый------------------
----------------------------------------------------------------------
----------------------------------------------------------------------
DigitalExciter1-SerNumer OBJECT-TYPE
  SYNTAX  DisplayString
  ACCESS  read-only
  STATUS  mandatory
  DESCRIPTION
          "Serial number of the device"
  ::= {DigitalExciter1-Info 1}
----------------------------------------------------------------------
DigitalExciter1-Software OBJECT-TYPE
  SYNTAX  DisplayString
  ACCESS  read-only
  STATUS  mandatory
  DESCRIPTION
          "Software application"
  ::= {DigitalExciter1-Info 2}
----------------------------------------------------------------------
DigitalExciter1-Software-Boot OBJECT-TYPE
  SYNTAX  DisplayString
  ACCESS  read-only
  STATUS  mandatory
  DESCRIPTION
          "Software bootloader"
  ::= {DigitalExciter1-Info 3}
----------------------------------------------------------------------
DigitalExciter1-Software-board OBJECT-TYPE
  SYNTAX  DisplayString
  ACCESS  read-only
  STATUS  mandatory
  DESCRIPTION
          "PCB version"
  ::= {DigitalExciter1-Info 4}
----------------------------------------------------------------------
----------------------------------------------------------------------
----------------------------------------------------------------------
DigitalExciter1-PowerOut OBJECT-TYPE
  SYNTAX  INTEGER
  ACCESS  read-only
  STATUS  current
  DESCRIPTION
          "Output power, W"
  ::= {DigitalExciter1-Param 1}
----------------------------------------------------------------------
DigitalExciter1-PowerRef OBJECT-TYPE
  SYNTAX  INTEGER
  ACCESS  read-only
  STATUS  current
  DESCRIPTION
          "PowerRef ,W"
  ::= {DigitalExciter1-Param 2}
----------------------------------------------------------------------
DigitalExciter1-SWR OBJECT-TYPE
  SYNTAX  INTEGER
  ACCESS  read-only
  STATUS  current
  DESCRIPTION
          "Value/100"
  ::= {DigitalExciter1-Param 3}
----------------------------------------------------------------------
DigitalExciter1-Pin OBJECT-TYPE
  SYNTAX  INTEGER
  ACCESS  read-only
  STATUS  current
  DESCRIPTION
          "Value, µW"
  ::= {DigitalExciter1-Param 4}
----------------------------------------------------------------------
DigitalExciter1-PowerBallast OBJECT-TYPE
  SYNTAX  INTEGER
  ACCESS  read-only
  STATUS  current
  DESCRIPTION
          "Ballast power, W"
  ::= {DigitalExciter1-Param 5}
----------------------------------------------------------------------
DigitalExciter1-U1 OBJECT-TYPE
  SYNTAX  INTEGER
  ACCESS  read-only
  STATUS  current
  DESCRIPTION
          "Value/10, V"
  ::= {DigitalExciter1-Param 10}
----------------------------------------------------------------------
DigitalExciter1-U2 OBJECT-TYPE
  SYNTAX  INTEGER
  ACCESS  read-only
  STATUS  current
  DESCRIPTION
          "Value/10, V"
  ::= {DigitalExciter1-Param 11}
----------------------------------------------------------------------
DigitalExciter1-I1 OBJECT-TYPE
  SYNTAX  INTEGER
  ACCESS  read-only
  STATUS  current
  DESCRIPTION
          "Value/10, A"
  ::= {DigitalExciter1-Param 20}
  ----------------------------------------------------------------------
DigitalExciter1-I2 OBJECT-TYPE
  SYNTAX  INTEGER
  ACCESS  read-only
  STATUS  current
  DESCRIPTION
          "Value/10, A"
  ::= {DigitalExciter1-Param 21}
  ----------------------------------------------------------------------
DigitalExciter1-I3 OBJECT-TYPE
  SYNTAX  INTEGER
  ACCESS  read-only
  STATUS  current
  DESCRIPTION
          "Value/10, A"
  ::= {DigitalExciter1-Param 22}  
  ----------------------------------------------------------------------
DigitalExciter1-I4 OBJECT-TYPE
  SYNTAX  INTEGER
  ACCESS  read-only
  STATUS  current
  DESCRIPTION
          "Value/10, A"
  ::= {DigitalExciter1-Param 23}    
----------------------------------------------------------------------
DigitalExciter1-Temperature OBJECT-TYPE
  SYNTAX  INTEGER
  ACCESS  read-only
  STATUS  current
  DESCRIPTION
          "Value/10, Celsius degree"
  ::= {DigitalExciter1-Param 30}
----------------------------------------------------------------------
--------------------------STATUS--------------------------------------
----------------------------------------------------------------------
DigitalExciter1-status-PowerOut OBJECT-TYPE
  SYNTAX  INTEGER{STATUS_LOW_FAIL(3),STATUS_OK(1),STATUS_ALARM(2),STATUS_FAIL(3),NOT_USED(255)}
  ACCESS  read-only
  STATUS  current
  DESCRIPTION
          "Output power, W"
  ::= {DigitalExciter1-Status 1}
----------------------------------------------------------------------
DigitalExciter1-status-PowerRef OBJECT-TYPE
  SYNTAX  INTEGER{STATUS_LOW_FAIL(3),STATUS_OK(1),STATUS_ALARM(2),STATUS_FAIL(3),NOT_USED(255)}
  ACCESS  read-only
  STATUS  current
  DESCRIPTION
          "PowerRef ,W"
  ::= {DigitalExciter1-Status 2}
----------------------------------------------------------------------
DigitalExciter1-status-SWR OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/100"
  ::= {DigitalExciter1-Status 3}
----------------------------------------------------------------------
DigitalExciter1-status-Pin OBJECT-TYPE
  SYNTAX  INTEGER{STATUS_LOW_FAIL(3),STATUS_OK(1),STATUS_ALARM(2),STATUS_FAIL(3),NOT_USED(255)}
  ACCESS  read-only
  STATUS  current
  DESCRIPTION
          "Value, µW"
  ::= {DigitalExciter1-Status 4}
----------------------------------------------------------------------
DigitalExciter1-status-PowerBallast OBJECT-TYPE
  SYNTAX  INTEGER{STATUS_LOW_FAIL(3),STATUS_OK(1),STATUS_ALARM(2),STATUS_FAIL(3),NOT_USED(255)}
  ACCESS  read-only
  STATUS  current
  DESCRIPTION
          "Ballast power, W"
  ::= {DigitalExciter1-Status 5}
----------------------------------------------------------------------
DigitalExciter1-status-U1 OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/10, V"
  ::= {DigitalExciter1-Status 10}
----------------------------------------------------------------------
DigitalExciter1-status-U2 OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/10, V"
  ::= {DigitalExciter1-Status 11}
----------------------------------------------------------------------
DigitalExciter1-status-I1 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter1-Status 20}
  ----------------------------------------------------------------------
DigitalExciter1-status-I2 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter1-Status 21}
  ----------------------------------------------------------------------
DigitalExciter1-status-I3 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter1-Status 22}  
  ----------------------------------------------------------------------
DigitalExciter1-status-I4 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter1-Status 23}  
----------------------------------------------------------------------
DigitalExciter1-status-Temperature OBJECT-TYPE
  SYNTAX  INTEGER{STATUS_LOW_FAIL(3),STATUS_OK(1),STATUS_ALARM(2),STATUS_FAIL(3),NOT_USED(255)}
  ACCESS  read-only
  STATUS  current
  DESCRIPTION
          "Celsius degree"
  ::= {DigitalExciter1-Status 30}  


----------------------------------------------------------------------
----------------------------------------------------------------------
---------------------Блок управлеие модель СТ второй------------------
----------------------------------------------------------------------
----------------------------------------------------------------------
DigitalExciter2-SerNumer OBJECT-TYPE
  SYNTAX  DisplayString
  ACCESS  read-only
  STATUS  mandatory
  DESCRIPTION
          "Serial number of the device"
  ::= {DigitalExciter2-Info 1}
----------------------------------------------------------------------
DigitalExciter2-Software OBJECT-TYPE
  SYNTAX  DisplayString
  ACCESS  read-only
  STATUS  mandatory
  DESCRIPTION
          "Software application"
  ::= {DigitalExciter2-Info 2}
----------------------------------------------------------------------
DigitalExciter2-Software-Boot OBJECT-TYPE
  SYNTAX  DisplayString
  ACCESS  read-only
  STATUS  mandatory
  DESCRIPTION
          "Software bootloader"
  ::= {DigitalExciter2-Info 3}
----------------------------------------------------------------------
DigitalExciter2-Software-board OBJECT-TYPE
  SYNTAX  DisplayString
  ACCESS  read-only
  STATUS  mandatory
  DESCRIPTION
          "PCB version"
  ::= {DigitalExciter2-Info 4}
----------------------------------------------------------------------
----------------------------------------------------------------------
----------------------------------------------------------------------
DigitalExciter2-PowerOut OBJECT-TYPE
  SYNTAX  INTEGER
  ACCESS  read-only
  STATUS  current
  DESCRIPTION
          "Output power, W"
  ::= {DigitalExciter2-Param 1}
----------------------------------------------------------------------
DigitalExciter2-PowerRef OBJECT-TYPE
  SYNTAX  INTEGER
  ACCESS  read-only
  STATUS  current
  DESCRIPTION
          "PowerRef ,W"
  ::= {DigitalExciter2-Param 2}
----------------------------------------------------------------------
DigitalExciter2-SWR OBJECT-TYPE
  SYNTAX  INTEGER
  ACCESS  read-only
  STATUS  current
  DESCRIPTION
          "Value/100"
  ::= {DigitalExciter2-Param 3}
----------------------------------------------------------------------
DigitalExciter2-Pin OBJECT-TYPE
  SYNTAX  INTEGER
  ACCESS  read-only
  STATUS  current
  DESCRIPTION
          "Value, µW"
  ::= {DigitalExciter2-Param 4}
----------------------------------------------------------------------
DigitalExciter2-PowerBallast OBJECT-TYPE
  SYNTAX  INTEGER
  ACCESS  read-only
  STATUS  current
  DESCRIPTION
          "Ballast power, W"
  ::= {DigitalExciter2-Param 5}
----------------------------------------------------------------------
DigitalExciter2-U1 OBJECT-TYPE
  SYNTAX  INTEGER
  ACCESS  read-only
  STATUS  current
  DESCRIPTION
          "Value/10, V"
  ::= {DigitalExciter2-Param 10}
----------------------------------------------------------------------
DigitalExciter2-U2 OBJECT-TYPE
  SYNTAX  INTEGER
  ACCESS  read-only
  STATUS  current
  DESCRIPTION
          "Value/10, V"
  ::= {DigitalExciter2-Param 11}
----------------------------------------------------------------------
DigitalExciter2-I1 OBJECT-TYPE
  SYNTAX  INTEGER
  ACCESS  read-only
  STATUS  current
  DESCRIPTION
          "Value/10, A"
  ::= {DigitalExciter2-Param 20}
  ----------------------------------------------------------------------
DigitalExciter2-I2 OBJECT-TYPE
  SYNTAX  INTEGER
  ACCESS  read-only
  STATUS  current
  DESCRIPTION
          "Value/10, A"
  ::= {DigitalExciter2-Param 21}
  ----------------------------------------------------------------------
DigitalExciter2-I3 OBJECT-TYPE
  SYNTAX  INTEGER
  ACCESS  read-only
  STATUS  current
  DESCRIPTION
          "Value/10, A"
  ::= {DigitalExciter2-Param 22}  
  ----------------------------------------------------------------------
DigitalExciter2-I4 OBJECT-TYPE
  SYNTAX  INTEGER
  ACCESS  read-only
  STATUS  current
  DESCRIPTION
          "Value/10, A"
  ::= {DigitalExciter2-Param 23}    
----------------------------------------------------------------------
DigitalExciter2-Temperature OBJECT-TYPE
  SYNTAX  INTEGER
  ACCESS  read-only
  STATUS  current
  DESCRIPTION
          "Value/10, Celsius degree"
  ::= {DigitalExciter2-Param 30}
----------------------------------------------------------------------
--------------------------STATUS--------------------------------------
----------------------------------------------------------------------
DigitalExciter2-status-PowerOut OBJECT-TYPE
  SYNTAX  INTEGER{STATUS_LOW_FAIL(3),STATUS_OK(1),STATUS_ALARM(2),STATUS_FAIL(3),NOT_USED(255)}
  ACCESS  read-only
  STATUS  current
  DESCRIPTION
          "Output power, W"
  ::= {DigitalExciter2-Status 1}
----------------------------------------------------------------------
DigitalExciter2-status-PowerRef OBJECT-TYPE
  SYNTAX  INTEGER{STATUS_LOW_FAIL(3),STATUS_OK(1),STATUS_ALARM(2),STATUS_FAIL(3),NOT_USED(255)}
  ACCESS  read-only
  STATUS  current
  DESCRIPTION
          "PowerRef ,W"
  ::= {DigitalExciter2-Status 2}
----------------------------------------------------------------------
DigitalExciter2-status-SWR OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/100"
  ::= {DigitalExciter2-Status 3}
----------------------------------------------------------------------
DigitalExciter2-status-Pin OBJECT-TYPE
  SYNTAX  INTEGER{STATUS_LOW_FAIL(3),STATUS_OK(1),STATUS_ALARM(2),STATUS_FAIL(3),NOT_USED(255)}
  ACCESS  read-only
  STATUS  current
  DESCRIPTION
          "Value, µW"
  ::= {DigitalExciter2-Status 4}
----------------------------------------------------------------------
DigitalExciter2-status-PowerBallast OBJECT-TYPE
  SYNTAX  INTEGER{STATUS_LOW_FAIL(3),STATUS_OK(1),STATUS_ALARM(2),STATUS_FAIL(3),NOT_USED(255)}
  ACCESS  read-only
  STATUS  current
  DESCRIPTION
          "Ballast power, W"
  ::= {DigitalExciter2-Status 5}
----------------------------------------------------------------------
DigitalExciter2-status-U1 OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/10, V"
  ::= {DigitalExciter2-Status 10}
----------------------------------------------------------------------
DigitalExciter2-status-U2 OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/10, V"
  ::= {DigitalExciter2-Status 11}
----------------------------------------------------------------------
DigitalExciter2-status-I1 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter2-Status 20}
  ----------------------------------------------------------------------
DigitalExciter2-status-I2 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter2-Status 21}
  ----------------------------------------------------------------------
DigitalExciter2-status-I3 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter2-Status 22}  
  ----------------------------------------------------------------------
DigitalExciter2-status-I4 OBJECT-TYPE
  SYNTAX  INTEGER{STATUS_LOW_FAIL(3),STATUS_OK(1),STATUS_ALARM(2),STATUS_FAIL(3),NOT_USED(255)}
  ACCESS  read-only
  STATUS  current
  DESCRIPTION
          "Value/10, A"
  ::= {DigitalExciter2-Status 23}  
----------------------------------------------------------------------
DigitalExciter2-status-Temperature OBJECT-TYPE
  SYNTAX  INTEGER{STATUS_LOW_FAIL(3),STATUS_OK(1),STATUS_ALARM(2),STATUS_FAIL(3),NOT_USED(255)}
  ACCESS  read-only
  STATUS  current
  DESCRIPTION
          "Celsius degree"
  ::= {DigitalExciter2-Status 30}  

----------------------------------------------------------------------
----------------------------------------------------------------------
----------------------Блок управление Система-------------------------
--------------Система автоматического резервирования 1+1--------------
----------------------------------------------------------------------
----------------------------------------------------------------------

----------------------------------------------------------------------
-----------------------Версия ПО -------------------------------------
----------------------------------------------------------------------
AVR1_1-SerNumer OBJECT-TYPE
  SYNTAX  DisplayString
  ACCESS  read-only
  STATUS  mandatory
  DESCRIPTION
          "Serial number of the device"
  ::= {AVR1_1-Info 1}
----------------------------------------------------------------------
AVR1_1-Software OBJECT-TYPE
  SYNTAX  DisplayString
  ACCESS  read-only
  STATUS  mandatory
  DESCRIPTION
          "Software application"
  ::= {AVR1_1-Info 2}
----------------------------------------------------------------------
AVR1_1-Software-Boot OBJECT-TYPE
  SYNTAX  DisplayString
  ACCESS  read-only
  STATUS  mandatory
  DESCRIPTION
          "Software bootloader"
  ::= {AVR1_1-Info 3}
----------------------------------------------------------------------
AVR1_1-Software-board OBJECT-TYPE
  SYNTAX  DisplayString
  ACCESS  read-only
  STATUS  mandatory
  DESCRIPTION
          "PCB version"
  ::= {AVR1_1-Info 4}


----------------------------------------------------------------------
------------------------Параметры ------------------------------------
----------------------------------------------------------------------
AVR1_1-Param-PowerOut OBJECT-TYPE
  SYNTAX  INTEGER
  ACCESS  read-only
  STATUS  current
  DESCRIPTION
          "Output power, W"
  ::= {AVR1_1-Param 1}
----------------------------------------------------------------------
AVR1_1-Param-PowerRef OBJECT-TYPE
  SYNTAX  INTEGER
  ACCESS  read-only
  STATUS  current
  DESCRIPTION
          "PowerRef ,W"
  ::= {AVR1_1-Param 2}
----------------------------------------------------------------------
AVR1_1-Param-SWR OBJECT-TYPE
  SYNTAX  INTEGER
  ACCESS  read-only
  STATUS  current
  DESCRIPTION
          "Value/100"
  ::= {AVR1_1-Param 3}
----------------------------------------------------------------------
AVR1_1-Param-AC220 OBJECT-TYPE
  SYNTAX  INTEGER
  ACCESS  read-only
  STATUS  current
  DESCRIPTION
          "The measured AC input voltage in volts."
  ::= {AVR1_1-Param 4}
----------------------------------------------------------------------
--------------------------STATUS--------------------------------------
----------------------------------------------------------------------
AVR1_1-status-PowerOut OBJECT-TYPE
  SYNTAX  INTEGER{STATUS_LOW_FAIL(3),STATUS_OK(1),STATUS_ALARM(2),STATUS_FAIL(3),NOT_USED(255)}
  ACCESS  read-only
  STATUS  current
  DESCRIPTION
          "Output power, W"
  ::= {AVR1_1-Status 1}
----------------------------------------------------------------------
AVR1_1-status-PowerRef OBJECT-TYPE
  SYNTAX  INTEGER{STATUS_LOW_FAIL(3),STATUS_OK(1),STATUS_ALARM(2),STATUS_FAIL(3),NOT_USED(255)}
  ACCESS  read-only
  STATUS  current
  DESCRIPTION
          "PowerRef ,W"
  ::= {AVR1_1-Status 2}
----------------------------------------------------------------------
AVR1_1-status-SWR OBJECT-TYPE
  SYNTAX  INTEGER{STATUS_OFF(0),STATUS_LOW_FAIL(3),STATUS_OK(1),STATUS_ALARM(2),STATUS_FAIL(3),NOT_USED(255)}
  ACCESS  read-only
  STATUS  current
  DESCRIPTION
          "Value/100"
  ::= {AVR1_1-Status 3}
----------------------------------------------------------------------
AVR1_1-status-Connection OBJECT-TYPE
  SYNTAX  INTEGER{connected(1),disconnected(0)}
  ACCESS  read-only
  STATUS  current
  DESCRIPTION
          ""
  ::= {AVR1_1-Status 4}






----------------------------------------------------------------------
----------------------------------------------------------------------
------------------Блок Автоматического Ввода Резерва------------------
---------------Система автоматического резервирования 3+1-------------
----------------------------------------------------------------------
----------------------------------------------------------------------

----------------------------------------------------------------------
-----------------------Версия ПО -------------------------------------
----------------------------------------------------------------------

----------------------------------------------------------------------
AVR-SerNumer OBJECT-TYPE
  SYNTAX  DisplayString
  ACCESS  read-only
  STATUS  mandatory
  DESCRIPTION
          "Serial number of the device"
  ::= {AVR-Info 1}
----------------------------------------------------------------------
AVR-Software OBJECT-TYPE
  SYNTAX  DisplayString
  ACCESS  read-only
  STATUS  mandatory
  DESCRIPTION
          "Software application"
  ::= {AVR-Info 2}
----------------------------------------------------------------------
AVR-Software-board OBJECT-TYPE
  SYNTAX  DisplayString
  ACCESS  read-only
  STATUS  mandatory
  DESCRIPTION
          "PCB version"
  ::= {AVR-Info 3}
----------------------------------------------------------------------
AVR-Software-Boot OBJECT-TYPE
  SYNTAX  DisplayString
  ACCESS  read-only
  STATUS  mandatory
  DESCRIPTION
          "Software bootloader"
  ::= {AVR-Info 4}
----------------------------------------------------------------------
AVR-SerNumer-BCA-analog OBJECT-TYPE
  SYNTAX  DisplayString
  ACCESS  read-only
  STATUS  mandatory
  DESCRIPTION
          "Serial number analog BCA"
  ::= {AVR-Info 10}
----------------------------------------------------------------------
AVR-Software-BCA-analog OBJECT-TYPE
  SYNTAX  DisplayString
  ACCESS  read-only
  STATUS  mandatory
  DESCRIPTION
          "Software version analog BCA"
  ::= {AVR-Info 11}
----------------------------------------------------------------------
AVR-Software-board-BCA-analog OBJECT-TYPE
  SYNTAX  DisplayString
  ACCESS  read-only
  STATUS  mandatory
  DESCRIPTION
          "PCB version analog BCA"
  ::= {AVR-Info 12}

----------------------------------------------------------------------
AVR-SerNumer-BCA-digital OBJECT-TYPE
  SYNTAX  DisplayString
  ACCESS  read-only
  STATUS  mandatory
  DESCRIPTION
          "Serial number digital BCA"
  ::= {AVR-Info 20}
----------------------------------------------------------------------
AVR-Software-BCA-digital OBJECT-TYPE
  SYNTAX  DisplayString
  ACCESS  read-only
  STATUS  mandatory
  DESCRIPTION
          "Software version digital BCA"
  ::= {AVR-Info 21}
----------------------------------------------------------------------
AVR-Software-board-BCA-digital OBJECT-TYPE
  SYNTAX  DisplayString
  ACCESS  read-only
  STATUS  mandatory
  DESCRIPTION
          "PCB version digital BCA"
  ::= {AVR-Info 22}





----------------------------------------------------------------------
-----------------------Настройки АВР----------------------------------
----------------------------------------------------------------------
AVR-Operating-mode OBJECT-TYPE
  SYNTAX  INTEGER{Auto(0),Manual(1)}
  ACCESS  read-write
  STATUS  mandatory
  DESCRIPTION
          "0- Auto 1- Manual"
  ::= {AVR-Setting 1}
----------------------------------------------------------------------
AVR-AFD OBJECT-TYPE
  SYNTAX  INTEGER{OFF(0),ON(1)}
  ACCESS  read-write
  STATUS  mandatory
  DESCRIPTION
          "Antenna-feeder Device
           OFF(0),ON(1)"
  ::= {AVR-Setting 2}
----------------------------------------------------------------------
----------- Включить/Выключить загрузчик-------------------------------
----------------------------------------------------------------------
AVR-Access-Boot OBJECT-TYPE
  SYNTAX  INTEGER{ACCESS_DENIED(0),ACCESS_ALLOWED(1)}
  ACCESS  read-write
  STATUS  mandatory
  DESCRIPTION
          "ACCESS_DENIED(0),ACCESS_ALLOWED(1))"
  ::= {AVR-Setting 3}

----------------------------------------------------------------------
----------- Перезагрузка AVR -----------------------------------------
----------------------------------------------------------------------
AVR-reboot OBJECT-TYPE
  SYNTAX  INTEGER{Reboot(1)}
  ACCESS  write-only
  STATUS  mandatory
  DESCRIPTION
          "Reboot AVR"
  ::= {AVR-Setting 10}

----------------------------------------------------------------------
-----------------------параметры АВР----------------------------------
----------------------------------------------------------------------
AVR-Temperature OBJECT-TYPE
  SYNTAX  INTEGER
  ACCESS  read-only
  STATUS  current
  DESCRIPTION
          "Value/10, Celsius degree"
  ::= {AVR-Param 30}
----------------------------------------------------------------------
-------------Параметры AVR комплекта 1 -------------------
----------------------------------------------------------------------
----------------------------------------------------------------------
Transmiter1-Name OBJECT-TYPE
  SYNTAX  DisplayString
  ACCESS  read-only
  STATUS  mandatory
  DESCRIPTION
          ""
  ::= {Transmiter1-Param 1}
----------------------------------------------------------------------
Transmiter1-Exist OBJECT-TYPE
  SYNTAX  INTEGER
  ACCESS  read-only
  STATUS  current
  DESCRIPTION
          "1 - Active 0 - Deactive "
  ::= {Transmiter1-Param 2}
----------------------------------------------------------------------
Transmiter1-Pout OBJECT-TYPE
  SYNTAX  INTEGER
  ACCESS  read-only
  STATUS  current
  DESCRIPTION
          "Output power, W"
  ::= {Transmiter1-Param 3}
----------------------------------------------------------------------
Transmiter1-Swr OBJECT-TYPE
  SYNTAX  INTEGER
  ACCESS  read-only
  STATUS  current
  DESCRIPTION
          "Value/100"
  ::= {Transmiter1-Param 4}
----------------------------------------------------------------------
Transmiter1-Pref OBJECT-TYPE
  SYNTAX  INTEGER
  ACCESS  read-only
  STATUS  current
  DESCRIPTION
          "Power Reflection, W"
  ::= {Transmiter1-Param 5}
----------------------------------------------------------------------
Transmiter1-Freq OBJECT-TYPE
  SYNTAX  INTEGER
  ACCESS  read-only
  STATUS  current
  DESCRIPTION
          "Value/100, MHz"
  ::= {Transmiter1-Param 6}  
----------------------------------------------------------------------
Transmiter1-Input OBJECT-TYPE
  SYNTAX  INTEGER
  ACCESS  read-only
  STATUS  current
  DESCRIPTION
          ""
  ::= {Transmiter1-Param 7}  
----------------------------------------------------------------------
Transmiter1-main-lvl_Left OBJECT-TYPE
  SYNTAX  INTEGER
  ACCESS  read-only
  STATUS  current
  DESCRIPTION
          "Value/10, dB"
  ::= {Transmiter1-Param 8}
----------------------------------------------------------------------
Transmiter1-main-lvl_Right OBJECT-TYPE
  SYNTAX  INTEGER
  ACCESS  read-only
  STATUS  current
  DESCRIPTION
          "Value/10, dB"
  ::= {Transmiter1-Param 9}
----------------------------------------------------------------------
Transmiter1-main-lvl_Mpx OBJECT-TYPE
  SYNTAX  INTEGER
  ACCESS  read-only
  STATUS  current
  DESCRIPTION
          "Value/10, dB"
  ::= {Transmiter1-Param 10}
----------------------------------------------------------------------
Transmiter1-main-lvl_Aes OBJECT-TYPE
  SYNTAX  INTEGER
  ACCESS  read-only
  STATUS  current
  DESCRIPTION
          "Value/10, v"
  ::= {Transmiter1-Param 11}
  ----------------------------------------------------------------------
  ----------------------------------------------------------------------
  ----------------------------------------------------------------------
  ----------------------------------------------------------------------
Transmiter1-reserv-lvl_Left OBJECT-TYPE
  SYNTAX  INTEGER
  ACCESS  read-only
  STATUS  current
  DESCRIPTION
          "Value/10, dB"
  ::= {Transmiter1-Param 12}
----------------------------------------------------------------------
Transmiter1-reserv-lvl_Right OBJECT-TYPE
  SYNTAX  INTEGER
  ACCESS  read-only
  STATUS  current
  DESCRIPTION
          "Value/10, dB"
  ::= {Transmiter1-Param 13}
----------------------------------------------------------------------
Transmiter1-reserv-lvl_Mpx OBJECT-TYPE
  SYNTAX  INTEGER
  ACCESS  read-only
  STATUS  current
  DESCRIPTION
          "Value/10, dB"
  ::= {Transmiter1-Param 14}
----------------------------------------------------------------------
Transmiter1-reserv-lvl_Aes OBJECT-TYPE
  SYNTAX  INTEGER
  ACCESS  read-only
  STATUS  current
  DESCRIPTION
          "Value/10, v"
  ::= {Transmiter1-Param 15}
----------------------------------------------------------------------

----------------------------------------------------------------------
---------------------Настройки ПРД-1----------------------------------
----------------------------------------------------------------------
Transmiter1-State OBJECT-TYPE
  SYNTAX  INTEGER{OFF(0),ON(1)}
  ACCESS  read-write
  STATUS  mandatory
  DESCRIPTION
          "OFF(0),ON(1)"
  ::= {Transmiter1-Setting 1}

----------------------------------------------------------------------
-----------------------Статусы AVR комплекта 1 -----------
----------------------------------------------------------------------

Transmiter1-status-Pout OBJECT-TYPE
  SYNTAX  INTEGER{STATUS_OK(0),STATUS_ALARM(1),STATUS_FAIL(2),STATUS_OFF(3)}
  ACCESS  read-only
  STATUS  current
  DESCRIPTION
          ""
  ::= {Transmiter1-Status 3}
----------------------------------------------------------------------
Transmiter1-status-Swr OBJECT-TYPE
  SYNTAX  INTEGER{STATUS_OK(0),STATUS_ALARM(1),STATUS_FAIL(2),STATUS_OFF(3)}
  ACCESS  read-only
  STATUS  current
  DESCRIPTION
          ""
  ::= {Transmiter1-Status 4}
----------------------------------------------------------------------
Transmiter1-status-Pref OBJECT-TYPE
  SYNTAX  INTEGER{STATUS_OK(0),STATUS_ALARM(1),STATUS_FAIL(2),STATUS_OFF(3)}
  ACCESS  read-only
  STATUS  current
  DESCRIPTION
          ""
  ::= {Transmiter1-Status 5}  
----------------------------------------------------------------------

Transmiter1-status-main-lvl_Left OBJECT-TYPE
  SYNTAX  INTEGER{STATUS_OK(0),STATUS_FAIL(2)}
  ACCESS  read-only
  STATUS  current
  DESCRIPTION
          ""
  ::= {Transmiter1-Status 8} 
----------------------------------------------------------------------
Transmiter1-status-main-lvl_Right OBJECT-TYPE
  SYNTAX  INTEGER{STATUS_OK(0),STATUS_FAIL(2)}
  ACCESS  read-only
  STATUS  current
  DESCRIPTION
          ""
  ::= {Transmiter1-Status 9} 

----------------------------------------------------------------------
Transmiter1-status-main-lvl_Mpx OBJECT-TYPE
  SYNTAX  INTEGER{STATUS_OK(0),STATUS_FAIL(2)}
  ACCESS  read-only
  STATUS  current
  DESCRIPTION
          ""
  ::= {Transmiter1-Status 10} 
----------------------------------------------------------------------
Transmiter1-status-main-lvl_Aes OBJECT-TYPE
  SYNTAX  INTEGER{STATUS_OK(0),STATUS_FAIL(2)}
  ACCESS  read-only
  STATUS  current
  DESCRIPTION
          ""
  ::= {Transmiter1-Status 11}   
----------------------------------------------------------------------

Transmiter1-status-reserv-lvl_Left OBJECT-TYPE
  SYNTAX  INTEGER{STATUS_OK(0),STATUS_FAIL(2)}
  ACCESS  read-only
  STATUS  current
  DESCRIPTION
          ""
  ::= {Transmiter1-Status 12} 
----------------------------------------------------------------------
Transmiter1-status-reserv-lvl_Right OBJECT-TYPE
  SYNTAX  INTEGER{STATUS_OK(0),STATUS_FAIL(2)}
  ACCESS  read-only
  STATUS  current
  DESCRIPTION
          ""
  ::= {Transmiter1-Status 13} 

----------------------------------------------------------------------
Transmiter1-status-reserv-lvl_Mpx OBJECT-TYPE
  SYNTAX  INTEGER{STATUS_OK(0),STATUS_FAIL(2)}
  ACCESS  read-only
  STATUS  current
  DESCRIPTION
          ""
  ::= {Transmiter1-Status 14} 
----------------------------------------------------------------------
Transmiter1-status-reserv-lvl_Aes OBJECT-TYPE
  SYNTAX  INTEGER{STATUS_OK(0),STATUS_FAIL(2)}
  ACCESS  read-only
  STATUS  current
  DESCRIPTION
          ""
  ::= {Transmiter1-Status 15}   
----------------------------------------------------------------------


----------------------------------------------------------------------
-------------Параметры AVR комплекта 2 -------------------
----------------------------------------------------------------------
----------------------------------------------------------------------
Transmiter2-Name OBJECT-TYPE
  SYNTAX  DisplayString
  ACCESS  read-only
  STATUS  mandatory
  DESCRIPTION
          ""
  ::= {Transmiter2-Param 1}
----------------------------------------------------------------------
Transmiter2-Exist OBJECT-TYPE
  SYNTAX  INTEGER
  ACCESS  read-only
  STATUS  current
  DESCRIPTION
          "1 - Active 0 - Deactive "
  ::= {Transmiter2-Param 2}
----------------------------------------------------------------------
Transmiter2-Pout OBJECT-TYPE
  SYNTAX  INTEGER
  ACCESS  read-only
  STATUS  current
  DESCRIPTION
          "Output power, W"
  ::= {Transmiter2-Param 3}
----------------------------------------------------------------------
Transmiter2-Swr OBJECT-TYPE
  SYNTAX  INTEGER
  ACCESS  read-only
  STATUS  current
  DESCRIPTION
          "Value/100"
  ::= {Transmiter2-Param 4}
----------------------------------------------------------------------
Transmiter2-Pref OBJECT-TYPE
  SYNTAX  INTEGER
  ACCESS  read-only
  STATUS  current
  DESCRIPTION
          "Power Reflection, W"
  ::= {Transmiter2-Param 5}
----------------------------------------------------------------------
Transmiter2-Freq OBJECT-TYPE
  SYNTAX  INTEGER
  ACCESS  read-only
  STATUS  current
  DESCRIPTION
          "Value/100, MHz"
  ::= {Transmiter2-Param 6}  
----------------------------------------------------------------------
Transmiter2-Input OBJECT-TYPE
  SYNTAX  INTEGER
  ACCESS  read-only
  STATUS  current
  DESCRIPTION
          ""
  ::= {Transmiter2-Param 7}  

----------------------------------------------------------------------
Transmiter2-main-lvl_Left OBJECT-TYPE
  SYNTAX  INTEGER
  ACCESS  read-only
  STATUS  current
  DESCRIPTION
          "Value/10, dB"
  ::= {Transmiter2-Param 8}
----------------------------------------------------------------------
Transmiter2-main-lvl_Right OBJECT-TYPE
  SYNTAX  INTEGER
  ACCESS  read-only
  STATUS  current
  DESCRIPTION
          "Value/10, dB"
  ::= {Transmiter2-Param 9}
----------------------------------------------------------------------
Transmiter2-main-lvl_Mpx OBJECT-TYPE
  SYNTAX  INTEGER
  ACCESS  read-only
  STATUS  current
  DESCRIPTION
          "Value/10, dB"
  ::= {Transmiter2-Param 10}
----------------------------------------------------------------------
Transmiter2-main-lvl_Aes OBJECT-TYPE
  SYNTAX  INTEGER
  ACCESS  read-only
  STATUS  current
  DESCRIPTION
          "Value/10, v"
  ::= {Transmiter2-Param 11}
  ----------------------------------------------------------------------
  ----------------------------------------------------------------------
Transmiter2-reserv-lvl_Left OBJECT-TYPE
  SYNTAX  INTEGER
  ACCESS  read-only
  STATUS  current
  DESCRIPTION
          "Value/10, dB"
  ::= {Transmiter2-Param 12}
----------------------------------------------------------------------
Transmiter2-reserv-lvl_Right OBJECT-TYPE
  SYNTAX  INTEGER
  ACCESS  read-only
  STATUS  current
  DESCRIPTION
          "Value/10, dB"
  ::= {Transmiter2-Param 13}
----------------------------------------------------------------------
Transmiter2-reserv-lvl_Mpx OBJECT-TYPE
  SYNTAX  INTEGER
  ACCESS  read-only
  STATUS  current
  DESCRIPTION
          "Value/10, dB"
  ::= {Transmiter2-Param 14}
----------------------------------------------------------------------
Transmiter2-reserv-lvl_Aes OBJECT-TYPE
  SYNTAX  INTEGER
  ACCESS  read-only
  STATUS  current
  DESCRIPTION
          "Value/10, v"
  ::= {Transmiter2-Param 15}
----------------------------------------------------------------------

----------------------------------------------------------------------
---------------------Настройки ПРД-2----------------------------------
----------------------------------------------------------------------
Transmiter2-State OBJECT-TYPE
  SYNTAX  INTEGER{OFF(0),ON(1)}
  ACCESS  read-write
  STATUS  mandatory
  DESCRIPTION
          "OFF(0),ON(1)"
  ::= {Transmiter2-Setting 1}

----------------------------------------------------------------------
-----------------------Статусы AVR комплекта 2 -----------
----------------------------------------------------------------------

Transmiter2-status-Pout OBJECT-TYPE
  SYNTAX  INTEGER{STATUS_OK(0),STATUS_ALARM(1),STATUS_FAIL(2),STATUS_OFF(3)}
  ACCESS  read-only
  STATUS  current
  DESCRIPTION
          ""
  ::= {Transmiter2-Status 3}
----------------------------------------------------------------------
Transmiter2-status-Swr OBJECT-TYPE
  SYNTAX  INTEGER{STATUS_OK(0),STATUS_ALARM(1),STATUS_FAIL(2),STATUS_OFF(3)}
  ACCESS  read-only
  STATUS  current
  DESCRIPTION
          ""
  ::= {Transmiter2-Status 4}
----------------------------------------------------------------------
Transmiter2-status-Pref OBJECT-TYPE
  SYNTAX  INTEGER{STATUS_OK(0),STATUS_ALARM(1),STATUS_FAIL(2),STATUS_OFF(3)}
  ACCESS  read-only
  STATUS  current
  DESCRIPTION
          ""
  ::= {Transmiter2-Status 5}  

Transmiter2-status-main-lvl_Left OBJECT-TYPE
  SYNTAX  INTEGER{STATUS_OK(0),STATUS_FAIL(2)}
  ACCESS  read-only
  STATUS  current
  DESCRIPTION
          ""
  ::= {Transmiter2-Status 8} 
----------------------------------------------------------------------
Transmiter2-status-main-lvl_Right OBJECT-TYPE
  SYNTAX  INTEGER{STATUS_OK(0),STATUS_FAIL(2)}
  ACCESS  read-only
  STATUS  current
  DESCRIPTION
          ""
  ::= {Transmiter2-Status 9} 

----------------------------------------------------------------------
Transmiter2-status-main-lvl_Mpx OBJECT-TYPE
  SYNTAX  INTEGER{STATUS_OK(0),STATUS_FAIL(2)}
  ACCESS  read-only
  STATUS  current
  DESCRIPTION
          ""
  ::= {Transmiter2-Status 10} 
----------------------------------------------------------------------
Transmiter2-status-main-lvl_Aes OBJECT-TYPE
  SYNTAX  INTEGER{STATUS_OK(0),STATUS_FAIL(2)}
  ACCESS  read-only
  STATUS  current
  DESCRIPTION
          ""
  ::= {Transmiter2-Status 11}   
----------------------------------------------------------------------

Transmiter2-status-reserv-lvl_Left OBJECT-TYPE
  SYNTAX  INTEGER{STATUS_OK(0),STATUS_FAIL(2)}
  ACCESS  read-only
  STATUS  current
  DESCRIPTION
          ""
  ::= {Transmiter2-Status 12} 
----------------------------------------------------------------------
Transmiter2-status-reserv-lvl_Right OBJECT-TYPE
  SYNTAX  INTEGER{STATUS_OK(0),STATUS_FAIL(2)}
  ACCESS  read-only
  STATUS  current
  DESCRIPTION
          ""
  ::= {Transmiter2-Status 13} 

----------------------------------------------------------------------
Transmiter2-status-reserv-lvl_Mpx OBJECT-TYPE
  SYNTAX  INTEGER{STATUS_OK(0),STATUS_FAIL(2)}
  ACCESS  read-only
  STATUS  current
  DESCRIPTION
          ""
  ::= {Transmiter2-Status 14} 
----------------------------------------------------------------------
Transmiter2-status-reserv-lvl_Aes OBJECT-TYPE
  SYNTAX  INTEGER{STATUS_OK(0),STATUS_FAIL(2)}
  ACCESS  read-only
  STATUS  current
  DESCRIPTION
          ""
  ::= {Transmiter2-Status 15}   
----------------------------------------------------------------------



----------------------------------------------------------------------
-------------Параметры AVR комплекта 3 -------------------
----------------------------------------------------------------------
----------------------------------------------------------------------
Transmiter3-Name OBJECT-TYPE
  SYNTAX  DisplayString
  ACCESS  read-only
  STATUS  mandatory
  DESCRIPTION
          ""
  ::= {Transmiter3-Param 1}
----------------------------------------------------------------------
Transmiter3-Exist OBJECT-TYPE
  SYNTAX  INTEGER
  ACCESS  read-only
  STATUS  current
  DESCRIPTION
          "1 - Active 0 - Deactive "
  ::= {Transmiter3-Param 2}
----------------------------------------------------------------------
Transmiter3-Pout OBJECT-TYPE
  SYNTAX  INTEGER
  ACCESS  read-only
  STATUS  current
  DESCRIPTION
          "Output power, W"
  ::= {Transmiter3-Param 3}
----------------------------------------------------------------------
Transmiter3-Swr OBJECT-TYPE
  SYNTAX  INTEGER
  ACCESS  read-only
  STATUS  current
  DESCRIPTION
          "Value/100"
  ::= {Transmiter3-Param 4}
----------------------------------------------------------------------
Transmiter3-Pref OBJECT-TYPE
  SYNTAX  INTEGER
  ACCESS  read-only
  STATUS  current
  DESCRIPTION
          "Power Reflection, W"
  ::= {Transmiter3-Param 5}
----------------------------------------------------------------------
Transmiter3-Freq OBJECT-TYPE
  SYNTAX  INTEGER
  ACCESS  read-only
  STATUS  current
  DESCRIPTION
          "Value/100, MHz"
  ::= {Transmiter3-Param 6}  
----------------------------------------------------------------------
Transmiter3-Input OBJECT-TYPE
  SYNTAX  INTEGER
  ACCESS  read-only
  STATUS  current
  DESCRIPTION
          ""
  ::= {Transmiter3-Param 7}  
----------------------------------------------------------------------
Transmiter3-main-lvl_Left OBJECT-TYPE
  SYNTAX  INTEGER
  ACCESS  read-only
  STATUS  current
  DESCRIPTION
          "Value/10, dB"
  ::= {Transmiter3-Param 8}
----------------------------------------------------------------------
Transmiter3-main-lvl_Right OBJECT-TYPE
  SYNTAX  INTEGER
  ACCESS  read-only
  STATUS  current
  DESCRIPTION
          "Value/10, dB"
  ::= {Transmiter3-Param 9}
----------------------------------------------------------------------
Transmiter3-main-lvl_Mpx OBJECT-TYPE
  SYNTAX  INTEGER
  ACCESS  read-only
  STATUS  current
  DESCRIPTION
          "Value/10, dB"
  ::= {Transmiter3-Param 10}
----------------------------------------------------------------------
Transmiter3-main-lvl_Aes OBJECT-TYPE
  SYNTAX  INTEGER
  ACCESS  read-only
  STATUS  current
  DESCRIPTION
          "Value/10, v"
  ::= {Transmiter3-Param 11}
  ----------------------------------------------------------------------
  ----------------------------------------------------------------------
  ----------------------------------------------------------------------
  ----------------------------------------------------------------------
Transmiter3-reserv-lvl_Left OBJECT-TYPE
  SYNTAX  INTEGER
  ACCESS  read-only
  STATUS  current
  DESCRIPTION
          "Value/10, dB"
  ::= {Transmiter3-Param 12}
----------------------------------------------------------------------
Transmiter3-reserv-lvl_Right OBJECT-TYPE
  SYNTAX  INTEGER
  ACCESS  read-only
  STATUS  current
  DESCRIPTION
          "Value/10, dB"
  ::= {Transmiter3-Param 13}
----------------------------------------------------------------------
Transmiter3-reserv-lvl_Mpx OBJECT-TYPE
  SYNTAX  INTEGER
  ACCESS  read-only
  STATUS  current
  DESCRIPTION
          "Value/10, dB"
  ::= {Transmiter3-Param 14}
----------------------------------------------------------------------
Transmiter3-reserv-lvl_Aes OBJECT-TYPE
  SYNTAX  INTEGER
  ACCESS  read-only
  STATUS  current
  DESCRIPTION
          "Value/10, v"
  ::= {Transmiter3-Param 15}
----------------------------------------------------------------------
---------------------Настройки ПРД-3----------------------------------
----------------------------------------------------------------------
Transmiter3-State OBJECT-TYPE
  SYNTAX  INTEGER{OFF(0),ON(1)}
  ACCESS  read-write
  STATUS  mandatory
  DESCRIPTION
          "OFF(0),ON(1)"
  ::= {Transmiter3-Setting 1}

----------------------------------------------------------------------
-----------------------Статусы AVR комплекта 3 -----------
----------------------------------------------------------------------

Transmiter3-status-Pout OBJECT-TYPE
  SYNTAX  INTEGER{STATUS_OK(0),STATUS_ALARM(1),STATUS_FAIL(2),STATUS_OFF(3)}
  ACCESS  read-only
  STATUS  current
  DESCRIPTION
          ""
  ::= {Transmiter3-Status 3}
----------------------------------------------------------------------
Transmiter3-status-Swr OBJECT-TYPE
  SYNTAX  INTEGER{STATUS_OK(0),STATUS_ALARM(1),STATUS_FAIL(2),STATUS_OFF(3)}
  ACCESS  read-only
  STATUS  current
  DESCRIPTION
          ""
  ::= {Transmiter3-Status 4}
----------------------------------------------------------------------
Transmiter3-status-Pref OBJECT-TYPE
  SYNTAX  INTEGER{STATUS_OK(0),STATUS_ALARM(1),STATUS_FAIL(2),STATUS_OFF(3)}
  ACCESS  read-only
  STATUS  current
  DESCRIPTION
          ""
  ::= {Transmiter3-Status 5}  
----------------------------------------------------------------------

Transmiter3-status-main-lvl_Left OBJECT-TYPE
  SYNTAX  INTEGER{STATUS_OK(0),STATUS_FAIL(2)}
  ACCESS  read-only
  STATUS  current
  DESCRIPTION
          ""
  ::= {Transmiter3-Status 8}
----------------------------------------------------------------------
Transmiter3-status-main-lvl_Right OBJECT-TYPE
  SYNTAX  INTEGER{STATUS_OK(0),STATUS_FAIL(2)}
  ACCESS  read-only
  STATUS  current
  DESCRIPTION
          ""
  ::= {Transmiter3-Status 9} 

----------------------------------------------------------------------
Transmiter3-status-main-lvl_Mpx OBJECT-TYPE
  SYNTAX  INTEGER{STATUS_OK(0),STATUS_FAIL(2)}
  ACCESS  read-only
  STATUS  current
  DESCRIPTION
          ""
  ::= {Transmiter3-Status 10}
----------------------------------------------------------------------
Transmiter3-status-main-lvl_Aes OBJECT-TYPE
  SYNTAX  INTEGER{STATUS_OK(0),STATUS_FAIL(2)}
  ACCESS  read-only
  STATUS  current
  DESCRIPTION
          ""
  ::= {Transmiter3-Status 11}   
----------------------------------------------------------------------

Transmiter3-status-reserv-lvl_Left OBJECT-TYPE
  SYNTAX  INTEGER{STATUS_OK(0),STATUS_FAIL(2)}
  ACCESS  read-only
  STATUS  current
  DESCRIPTION
          ""
  ::= {Transmiter3-Status 12} 
----------------------------------------------------------------------
Transmiter3-status-reserv-lvl_Right OBJECT-TYPE
  SYNTAX  INTEGER{STATUS_OK(0),STATUS_FAIL(2)}
  ACCESS  read-only
  STATUS  current
  DESCRIPTION
          ""
  ::= {Transmiter3-Status 13} 

----------------------------------------------------------------------
Transmiter3-status-reserv-lvl_Mpx OBJECT-TYPE
  SYNTAX  INTEGER{STATUS_OK(0),STATUS_FAIL(2)}
  ACCESS  read-only
  STATUS  current
  DESCRIPTION
          ""
  ::= {Transmiter3-Status 14} 
----------------------------------------------------------------------
Transmiter3-status-reserv-lvl_Aes OBJECT-TYPE
  SYNTAX  INTEGER{STATUS_OK(0),STATUS_FAIL(2)}
  ACCESS  read-only
  STATUS  current
  DESCRIPTION
          ""
  ::= {Transmiter3-Status 15}   
----------------------------------------------------------------------







----------------------------------------------------------------------
-----------Параметры AVR  Резервного передатчика ----------
----------------------------------------------------------------------
----------------------------------------------------------------------
TransmiterReserv-Name OBJECT-TYPE
  SYNTAX  DisplayString
  ACCESS  read-only
  STATUS  mandatory
  DESCRIPTION
          ""
  ::= {TransmiterReserv-Param 1}
----------------------------------------------------------------------
TransmiterReserv-Exist OBJECT-TYPE
  SYNTAX  INTEGER
  ACCESS  read-only
  STATUS  current
  DESCRIPTION
          "1 - Active 0 - Deactive "
  ::= {TransmiterReserv-Param 2}
----------------------------------------------------------------------
TransmiterReserv-Pout OBJECT-TYPE
  SYNTAX  INTEGER
  ACCESS  read-only
  STATUS  current
  DESCRIPTION
          "Output power, W"
  ::= {TransmiterReserv-Param 3}
----------------------------------------------------------------------
TransmiterReserv-Swr OBJECT-TYPE
  SYNTAX  INTEGER
  ACCESS  read-only
  STATUS  current
  DESCRIPTION
          "Value/100"
  ::= {TransmiterReserv-Param 4}
----------------------------------------------------------------------
TransmiterReserv-Pref OBJECT-TYPE
  SYNTAX  INTEGER
  ACCESS  read-only
  STATUS  current
  DESCRIPTION
          "Power Reflection, W"
  ::= {TransmiterReserv-Param 5}
----------------------------------------------------------------------
TransmiterReserv-Freq OBJECT-TYPE
  SYNTAX  INTEGER
  ACCESS  read-only
  STATUS  current
  DESCRIPTION
          "Value/100, MHz"
  ::= {TransmiterReserv-Param 6}  
----------------------------------------------------------------------
TransmiterReserv-Input OBJECT-TYPE
  SYNTAX  INTEGER
  ACCESS  read-only
  STATUS  current
  DESCRIPTION
          ""
  ::= {TransmiterReserv-Param 7}  
----------------------------------------------------------------------
TransmiterReserv-lvl_Left OBJECT-TYPE
  SYNTAX  INTEGER
  ACCESS  read-only
  STATUS  current
  DESCRIPTION
          "Value/10, dB"
  ::= {TransmiterReserv-Param 8}
----------------------------------------------------------------------
TransmiterReserv-lvl_Right OBJECT-TYPE
  SYNTAX  INTEGER
  ACCESS  read-only
  STATUS  current
  DESCRIPTION
          "Value/10, dB"
  ::= {TransmiterReserv-Param 9}
----------------------------------------------------------------------
TransmiterReserv-lvl_Mpx OBJECT-TYPE
  SYNTAX  INTEGER
  ACCESS  read-only
  STATUS  current
  DESCRIPTION
          "Value/10, dB"
  ::= {TransmiterReserv-Param 10}
----------------------------------------------------------------------
TransmiterReserv-lvl_Aes OBJECT-TYPE
  SYNTAX  INTEGER
  ACCESS  read-only
  STATUS  current
  DESCRIPTION
          ""
  ::= {TransmiterReserv-Param 11}  
----------------------------------------------------------------------

----------------------------------------------------------------------
---------------------Настройки ПРД-резерва ---------------------------
----------------------------------------------------------------------
TransmiterReserv-State OBJECT-TYPE
  SYNTAX  INTEGER{OFF(0),ON(1)}
  ACCESS  read-write
  STATUS  mandatory
  DESCRIPTION
          "OFF(0),ON(1)"
  ::= {TransmiterReserv-Setting 1}
----------------------------------------------------------------------
AVR-apply-configuration OBJECT-TYPE
  SYNTAX  INTEGER{Transmitter1(1),Transmitter2(2),Transmitter3(3)}
  ACCESS  read-write
  STATUS  mandatory
  DESCRIPTION
          "Apply configuration from 1,2,3 transmitters"
  ::= {TransmiterReserv-Setting 2}  
----------------------------------------------------------------------
----------- Перезагрузка резервного передатчика ----------------------
----------------------------------------------------------------------
AVR-reboot_reserv OBJECT-TYPE
  SYNTAX  INTEGER{ON(1)}
  ACCESS  write-only
  STATUS  mandatory
  DESCRIPTION
          "Reboot Reserv"
  ::= {TransmiterReserv-Setting 10}
----------------------------------------------------------------------
----------------------------------------------------------------------
----------------Статусы AVR резервного передатчика---------
----------------------------------------------------------------------

TransmiterReserv-status-Pout OBJECT-TYPE
  SYNTAX  INTEGER{STATUS_OK(0),STATUS_ALARM(1),STATUS_FAIL(2),STATUS_OFF(3)}
  ACCESS  read-only
  STATUS  current
  DESCRIPTION
          ""
  ::= {TransmiterReserv-Status 3}
----------------------------------------------------------------------
TransmiterReserv-status-Swr OBJECT-TYPE
  SYNTAX  INTEGER{STATUS_OK(0),STATUS_ALARM(1),STATUS_FAIL(2),STATUS_OFF(3)}
  ACCESS  read-only
  STATUS  current
  DESCRIPTION
          ""
  ::= {TransmiterReserv-Status 4}
----------------------------------------------------------------------
TransmiterReserv-status-Pref OBJECT-TYPE
  SYNTAX  INTEGER{STATUS_OK(0),STATUS_ALARM(1),STATUS_FAIL(2),STATUS_OFF(3)}
  ACCESS  read-only
  STATUS  current
  DESCRIPTION
          ""
  ::= {TransmiterReserv-Status 5}  
----------------------------------------------------------------------
TransmiterReserv-status-lvl_Left OBJECT-TYPE
  SYNTAX  INTEGER{STATUS_OK(0),STATUS_ALARM(1),STATUS_FAIL(2),STATUS_OFF(3)}
  ACCESS  read-only
  STATUS  current
  DESCRIPTION
          ""
  ::= {TransmiterReserv-Status 8} 
----------------------------------------------------------------------
TransmiterReserv-status-lvl_Right OBJECT-TYPE
  SYNTAX  INTEGER{STATUS_OK(0),STATUS_ALARM(1),STATUS_FAIL(2),STATUS_OFF(3)}
  ACCESS  read-only
  STATUS  current
  DESCRIPTION
          ""
  ::= {TransmiterReserv-Status 9} 

----------------------------------------------------------------------
TransmiterReserv-status-lvl_Mpx OBJECT-TYPE
  SYNTAX  INTEGER{STATUS_OK(0),STATUS_ALARM(1),STATUS_FAIL(2),STATUS_OFF(3)}
  ACCESS  read-only
  STATUS  current
  DESCRIPTION
          ""
  ::= {TransmiterReserv-Status 10} 
----------------------------------------------------------------------
TransmiterReserv-status-lvl_Aes OBJECT-TYPE
  SYNTAX  INTEGER{STATUS_OK(0),STATUS_ALARM(1),STATUS_FAIL(2),STATUS_OFF(3)}
  ACCESS  read-only
  STATUS  current
  DESCRIPTION
          ""
  ::= {TransmiterReserv-Status 11}  
----------------------------------------------------------------------
Reserv-Status OBJECT-TYPE
  SYNTAX  INTEGER{OFF(0),INIT(1),SET_FREQ(2),SET_POWER(3),ERR_FREQ(4),ERR_POWER(5),ERR_CONNECT(6),ERR(7),ON(8)}
  ACCESS  read-only
  STATUS  current
  DESCRIPTION
          ""
  ::= {TransmiterReserv-Status 20} 
----------------------------------------------------------------------
----------------------------------------------------------------------
----------------------------------------------------------------------



----------------------------------------------------------------------
-----------------------Версия ПО -------------------------------------
----------------------------------------------------------------------

----------------------------------------------------------------------
Repeater-SerNumer OBJECT-TYPE
  SYNTAX  DisplayString
  ACCESS  read-only
  STATUS  mandatory
  DESCRIPTION
          "Serial number of the device"
  ::= {Repeater-Info 1}
----------------------------------------------------------------------
Repeater-Software OBJECT-TYPE
  SYNTAX  DisplayString
  ACCESS  read-only
  STATUS  mandatory
  DESCRIPTION
          "Software application"
  ::= {Repeater-Info 2}
----------------------------------------------------------------------
Repeater-Software-Boot OBJECT-TYPE
  SYNTAX  DisplayString
  ACCESS  read-only
  STATUS  mandatory
  DESCRIPTION
          "Software bootloader"
  ::= {Repeater-Info 3}
----------------------------------------------------------------------
Repeater-Software-board OBJECT-TYPE
  SYNTAX  DisplayString
  ACCESS  read-only
  STATUS  mandatory
  DESCRIPTION
          "PCB version"
  ::= {Repeater-Info 4}
----------------------------------------------------------------------
-----------------------Param Repeater--------------------------------
----------------------------------------------------------------------
Repeater-PowerOut OBJECT-TYPE
  SYNTAX  INTEGER
  ACCESS  read-only
  STATUS  current
  DESCRIPTION
          "Output power value/10, milliwatts"
  ::= {Repeater-Param 1}
----------------------------------------------------------------------
Repeater-PowerRef OBJECT-TYPE
  SYNTAX  INTEGER
  ACCESS  read-only
  STATUS  current
  DESCRIPTION
          "PowerRef value/10, milliwatts"
  ::= {Repeater-Param 2}
----------------------------------------------------------------------
Repeater-SWR OBJECT-TYPE
  SYNTAX  INTEGER
  ACCESS  read-only
  STATUS  current
  DESCRIPTION
          "Value/100"
  ::= {Repeater-Param 3}
----------------------------------------------------------------------
Repeater-Pin OBJECT-TYPE
  SYNTAX  INTEGER
  ACCESS  read-only
  STATUS  current
  DESCRIPTION
          "Input power value/10, milliwatts"
  ::= {Repeater-Param 4}
----------------------------------------------------------------------
Repeater-U1 OBJECT-TYPE
  SYNTAX  INTEGER
  ACCESS  read-only
  STATUS  current
  DESCRIPTION
          "Value/10, V"
  ::= {Repeater-Param 10}
----------------------------------------------------------------------
Repeater-I1 OBJECT-TYPE
  SYNTAX  INTEGER
  ACCESS  read-only
  STATUS  current
  DESCRIPTION
          "Value/10, A"
  ::= {Repeater-Param 20}
----------------------------------------------------------------------
Repeater-I2 OBJECT-TYPE
  SYNTAX  INTEGER
  ACCESS  read-only
  STATUS  current
  DESCRIPTION
          "Value/10, A"
  ::= {Repeater-Param 21}
----------------------------------------------------------------------
----------------------------------------------------------------------
Repeater-Temperature OBJECT-TYPE
  SYNTAX  INTEGER
  ACCESS  read-only
  STATUS  current
  DESCRIPTION
          "Celsius degree"
  ::= {Repeater-Param 30}
----------------------------------------------------------------------
Repeater-Input-channel OBJECT-TYPE
  SYNTAX  INTEGER
  ACCESS  read-only
  STATUS  current
  DESCRIPTION
          "input channel number"
  ::= {Repeater-Param 40}  
----------------------------------------------------------------------
Repeater-Output-channel OBJECT-TYPE
  SYNTAX  INTEGER
  ACCESS  read-only
  STATUS  current
  DESCRIPTION
          "output channel number"
  ::= {Repeater-Param 41}  

----------------------------------------------------------------------
-----------------Repeater-Setting------------------------------------
----------------------------------------------------------------------

----------------------------------------------------------------------
Repeater-State OBJECT-TYPE
  SYNTAX  INTEGER{OFF(0),ON(1)}
  ACCESS  read-write
  STATUS  mandatory
  DESCRIPTION
          "OFF(0),ON(1)"
  ::= {Repeater-Setting 10}
----------------------------------------------------------------------
Repeater-Access-Boot OBJECT-TYPE
  SYNTAX  INTEGER{ACCESS_DENIED(0),ACCESS_ALLOWED(1)}
  ACCESS  write-only
  STATUS  mandatory
  DESCRIPTION
          "ACCESS_DENIED(0),ACCESS_ALLOWED(1))"
  ::= {Repeater-Setting 20}
----------------------------------------------------------------------
----------- Перезагрузка Repeater ------------------------------------
----------------------------------------------------------------------
Repeater-Reboot OBJECT-TYPE
  SYNTAX  INTEGER{Reboot(1)}
  ACCESS  write-only
  STATUS  mandatory
  DESCRIPTION
          "Reboot Repeater"
  ::= {Repeater-Setting 30}
----------------------------------------------------------------------
----------- Перезагрузка Repeater ------------------------------------
----------------------------------------------------------------------
Repeater-IncreasePowerBig OBJECT-TYPE
  SYNTAX  INTEGER{Step(1)}
  ACCESS  write-only
  STATUS  mandatory
  DESCRIPTION
          "Increase in output power, big step"
  ::= {Repeater-Setting 40}
----------------------------------------------------------------------
Repeater-IncreasePowerSmall OBJECT-TYPE
  SYNTAX  INTEGER{Step(1)}
  ACCESS  write-only
  STATUS  mandatory
  DESCRIPTION
          "Increase in output power, small step"
  ::= {Repeater-Setting 41}
----------------------------------------------------------------------
Repeater-DecreasePowerBig OBJECT-TYPE
  SYNTAX  INTEGER{Step(1)}
  ACCESS  write-only
  STATUS  mandatory
  DESCRIPTION
          "Decrease in output power, big step"
  ::= {Repeater-Setting 42}
----------------------------------------------------------------------
Repeater-DecreasePowerSmall OBJECT-TYPE
  SYNTAX  INTEGER{Step(1)}
  ACCESS  write-only
  STATUS  mandatory
  DESCRIPTION
          "Decrease in output power, small step"
  ::= {Repeater-Setting 43}      
----------------------------------------------------------------------
Repeater-DecreasePowerSave OBJECT-TYPE
  SYNTAX  INTEGER{Save(1)}
  ACCESS  write-only
  STATUS  mandatory
  DESCRIPTION
          "Save output power"
  ::= {Repeater-Setting 50}      

----------------------------------------------------------------------
-----------------------status Repeater--------------------------------
----------------------------------------------------------------------

Repeater-status-PowerOut OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Repeater-Status 1}
----------------------------------------------------------------------
Repeater-status-PowerRef OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Repeater-Status 2}
----------------------------------------------------------------------
Repeater-status-SWR OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Repeater-Status 3}  
----------------------------------------------------------------------
Repeater-status-Pin OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Repeater-Status 4}  
----------------------------------------------------------------------
Repeater-status-U1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Repeater-Status 10}
----------------------------------------------------------------------
Repeater-status-I1 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Repeater-Status 20}  
----------------------------------------------------------------------
Repeater-status-I2 OBJECT-TYPE
    SYNTAX  INTEGER{STATUS_LOW_FAIL(3),STATUS_OK(1),STATUS_ALARM(2),STATUS_FAIL(3),NOT_USED(255)}
  ACCESS  read-only
  STATUS  current
  DESCRIPTION
          ""
  ::= {Repeater-Status 21}
----------------------------------------------------------------------
Repeater-status-T OBJECT-TYPE
  SYNTAX  INTEGER{TempIsNotExist(0),TempIsNorm(1),TempIsOverheat(3)}
  ACCESS  read-only
  STATUS  current
  DESCRIPTION
          ""
  ::= {Repeater-Status 30}





----------------------------------------------------------------------

END
